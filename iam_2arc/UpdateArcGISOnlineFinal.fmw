FME workspace UpdateArcGISOnlineFinal.fmw
Title: JSON to ARCGISONLINEFEATURES

Parameters:
- SourceDataset_JSON =

Readers:
- JSON_1: JSON from $(SourceDataset_JSON)
- ARCGISONLINEFEATURES_2: ARCGISONLINEFEATURES

Writers:
- ARCGISONLINEFEATURES_1: ARCGISONLINEFEATURES

Note: Update Schema to match existing Feature Service
AttributeManager
    ATTR_TABLE:
      REMOVE json_ogc_wkt_crs
      REMOVE json_geometry.type
      REMOVE json_geometry.coordinates{}
    -> ChangeDetector [REVISED]
Note: Find everything that has changed. / Automatically adds the fme_db_operation attribute
ChangeDetector
    BLANK_AND_MISSING_DIFFER = No
    CHECK_TYPES_AND_ENCODINGS = No
    MATCHATTRS = Weekend_St Park_Name Site_Area
    MATCH_STRATEGY = Match Selected Attributes
    PREEMPTIVE_ATTRS = RecordID
    UNCHANGED_OUTPUT = Output Original
    UPDATED_LIST_NAME = _changes
    UPDATED -> FeatureJoiner [RIGHT]
Note: Add OBJECTID onto features that will be updated
FeatureJoiner
    ATTR_CONFLICT_RES = Use Right
    GEOMETRY_HANDLING = Use Left
    JOIN_KEYS = RecordID RecordID AUTO
    JOIN_MODE = Inner
    JOINED -> PlayingFieldStatus (writer ARCGISONLINEFEATURES_1)

Bookmark: Dataset with updates
PlayingFieldStatus (reader JSON_1)
    attributes: RecordID string, Weekend_St string, Park_Name string, Site_Area string, json_ogc_wkt_crs string, json_geometry.type string, json_geometry.coordinates{} float, Closure_No string
    -> AttributeManager

Bookmark: Original ArcGIS Online Feature Service
PlayingFieldStatus (reader ARCGISONLINEFEATURES_2)
    attributes: RecordID String(254), Weekend_St String(254), Park_Name String(254), Site_Area String(254), Closure_No String(254), OBJECTID OID
    -> ChangeDetector [ORIGINAL]
    -> FeatureJoiner [LEFT]

Bookmark: Write updates to ArcGIS Online Feature Service
PlayingFieldStatus (writer ARCGISONLINEFEATURES_1)
    attributes: RecordID String(254), Weekend_St String(254), Park_Name String(254), Site_Area String(254), Closure_No String(254), OBJECTID OID
