FME workspace UpdatingIndividualFields.fmwt
Title: Updating Individual Fields of a Record

Parameters:
- SourceDataset_POSTGIS = FMETraining   # Connection
- SourceDataset_MITAB = $(FME_MF_DIR)1/Data/ParksUpdates.tab   # Source MapInfo TAB File(s)
- DestDataset_POSTGIS = FMETraining   # Connection

Readers:
- POSTGIS_1: POSTGIS from $(SourceDataset_POSTGIS)
- MITAB_1: MITAB from $(SourceDataset_MITAB)

Writers:
- POSTGIS_2: POSTGIS to $(DestDataset_POSTGIS)

DowntownParks (reader POSTGIS_1)
    attributes: parkid int2, refparkid int2, parkname varchar(40), neighborhoodname varchar(40), visitorcount int2, treecount int2, dogpark varchar(1), washrooms varchar(1), specialfeatures varchar(1)
    -> ChangeDetector [ORIGINAL]
ParksUpdates (reader MITAB_1)
    attributes: parkid smallint, refparkid smallint, parkname char(40), neighborhoodname char(40), visitorcount smallint, treecount smallint, dogpark char(1), washrooms char(1), specialfeatures char(1)
    -> ChangeDetector [REVISED]
ChangeDetector
    BLANK_AND_MISSING_DIFFER = No
    CHECK_COORDINATE_SYSTEMS = No
    CHECK_TYPES_AND_ENCODINGS = No
    LENIENT_MATCH = No
    MATCH = 2D
    MATCHATTRS = treecount visitorcount
    MATCH_STRATEGY = Match Selected Attributes
    PREEMPTIVE_ATTRS = parkid
    UNCHANGED_OUTPUT = Output Original
    UPDATED -> AttributeRemover
    INSERTED -> AttributeRemover
    DELETED -> AttributeRemover
AttributeRemover
    REMOVE_ATTRS = treecount,visitorcount
    -> DowntownParks (writer POSTGIS_2)
DowntownParks (writer POSTGIS_2)
    attributes: parkid int2, refparkid int2, parkname varchar(40), neighborhoodname varchar(40), visitorcount int2, treecount int2, dogpark varchar(1), washrooms varchar(1), specialfeatures varchar(1)
