FME workspace stormwater.fmw

Readers:
- GEODATABASE_SDE_1: GEODATABASE_SDE

swTreatmentDevice (reader GEODATABASE_SDE_1)
    attributes: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
swTreatmentDeviceArea (reader GEODATABASE_SDE_1) [off]
    attributes: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
swMain (reader GEODATABASE_SDE_1)
    attributes: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
swChannel (reader GEODATABASE_SDE_1)
    attributes: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
swInlet (reader GEODATABASE_SDE_1)
    attributes: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
swLateral (reader GEODATABASE_SDE_1)
    attributes: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
swManhole (reader GEODATABASE_SDE_1)
    attributes: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
swMeter (reader GEODATABASE_SDE_1)
    attributes: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
swNode (reader GEODATABASE_SDE_1)
    attributes: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
swPumpstation (reader GEODATABASE_SDE_1)
    attributes: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
swStructure (reader GEODATABASE_SDE_1)
    attributes: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
swValve (reader GEODATABASE_SDE_1)
    attributes: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
