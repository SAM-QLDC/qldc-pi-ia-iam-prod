FME workspace Enterprise_GISChanges_NewAssetsOnly.fmw

Parameters:
- SourceDataset_CSV2 = \\sqldcfile01\gisdata\projects\EAM\GIS_Synchronisation\Enterprise_LayerInfoLookup.csv   # Source CSV (Comma Separated Value) File(s)
- SourceDataset_CSV2_7 = \\sqldctone01\saas-out\CES\GISID_ASSETNUMBER_MATCH.csv   # Source CSV (Comma Separated Value) File(s)
- DestDataset_CSV2_12 = \\sqldcfile01\gisdata\Projects\EAM\GIS_Synchronisation\TechOneFormats\New_Assets   # Destination CSV (Comma Separated Value) Folder
- SourceDataset_CSV2_4 = \\sqldcfile01\gisdata\projects\EAM\GIS_Synchronisation\OldGlobalIDtoNew\GlobalIDMatch.csv   # Source CSV (Comma Separated Value) File(s)
- FME_USER_PARAM_PRIVATE_GRP =   # last_run_date Private Parameters
- last_run_date:   # Python Script
      from datetime import datetime
      
      today = datetime.today().strftime('%Y-%m-%d %H:%M:%S')
      file1 = open(r"\\sqldcfile01\gisdata\Projects\EAM\GIS_Synchronisation\Rundate.txt", "r")
      last_run = file1.read()
      last_run_date = datetime.strptime(last_run, '%Y-%m-%d %H:%M:%S')
      file1.close()
      file1 = open(r"\\sqldcfile01\gisdata\Projects\EAM\GIS_Synchronisation\Rundate.txt", 'w')
      file1.write(today)
      file1.close()
      return last_run_date

Readers:
- GEODATABASE_SDE_1: GEODATABASE_SDE
- CSV2_1: CSV2 from $(SourceDataset_CSV2)
- CSV2_2: CSV2 from $(SourceDataset_CSV2_7)
- CSV2_3: CSV2 from $(SourceDataset_CSV2_4)

Writers:
- CSV2_4: CSV2 to $(DestDataset_CSV2_12)

wsHydrant (reader GEODATABASE_SDE_1)
    attributes: OBJECTID integer, COMPKEY integer, ASSETTYPE char(254), DESCR char(254), SERVSTAT char(254), OWN char(254), ZCOORD double, INVERTELEV double, MODELNO char(20), MANUFCT char(20), INSTDATE date, ASBUILT char(30), SCHEME char(254), DATA_SRC char(20), COMMENTS char(254), ADDDBY char(20), ADDDTTM date, MODBY char(20), MODDTTM date, CONFIDENCE char(10), CRITICALITY double, ALLOCATE range_domain(ALLOCATE_4:integer:0:100), OLDGUID char(40), GlobalID globalid, created_user char(255), created_date date, last_edited_user char(255), last_edited_date date
    -> HydrantConvert
HydrantConvert: AttributeValueMapper
    DEFAULT_VALUE = @Value(ASSETTYPE)
    DIRECTION = Forward (Source To Destination)
    LUT = HYDRANT,FIRE_SER
    SRC = ASSETTYPE
    VAL_ATTR = ASSETTYPE
    -> ArcStroker
wsLateral (reader GEODATABASE_SDE_1)
    attributes: OBJECTID integer, COMPKEY integer, ASSETTYPE char(20), SRVTYPE char(254), DESCR char(254), SERVSTAT char(254), OWN char(254), PIPEMATL char(254), PIPELEN double, NOMDIAM double, INTDIAM double, OUTDIAM double, CLASS char(254), MANUFCT char(20), INSTDATE date, ASBUILT char(30), SCHEME char(254), DATA_SRC char(20), COMMENTS char(254), ADDDBY char(20), ADDDTTM date, MODBY char(20), MODDTTM date, CONFIDENCE char(10), CRITICALITY double, ALLOCATE range_domain(ALLOCATE_4:integer:0:100), OLDGUID char(40), GlobalID globalid, created_user char(255), created_date date,
      last_edited_user char(255), last_edited_date date, SHAPE.STLength() double
    -> Lateral_to_SERVICE
Lateral_to_SERVICE: AttributeValueMapper
    DEFAULT_VALUE = @Value(ASSETTYPE)
    DIRECTION = Forward (Source To Destination)
    LUT = LATERAL,SERVICE
    SRC = ASSETTYPE
    VAL_ATTR = ASSETTYPE
    -> ArcStroker
wwMain (reader GEODATABASE_SDE_1)
    attributes: OBJECTID integer, COMPKEY integer, ASSETTYPE char(254), DESCR char(254), SERVSTAT char(254), OWN char(254), PIPEMATL char(254), PIPELEN double, NOMDIAM double, INTDIAM double, OUTDIAM double, UPNODE char(20), UPSELEV double, DWNNODE char(20), DWNELEV double, CLASS char(254), INSTDATE date, JTTYPE char(254), MANUFCT char(20), INSTMTHD char(254), LINEMATL char(254), LINEMTHD char(254), LINEDATE date, ASBUILT char(30), SCHEME char(254), DATA_SRC char(20), COMMENTS char(254), ADDDBY char(20), ADDDTTM date, MODBY char(20),
      MODDTTM date, CONFIDENCE char(10), CRITICALITY double, ALLOCATE range_domain(ALLOCATE_4:integer:0:100), OLDGUID char(40), GlobalID globalid, created_user char(255), created_date date, last_edited_user char(255), last_edited_date date, SHAPE.STLength() double
    -> Sewer_to_GRAV
Sewer_to_GRAV: AttributeValueMapper
    DEFAULT_VALUE = @Value(ASSETTYPE)
    DIRECTION = Forward (Source To Destination)
    LUT = SEWER,GRAV
    SRC = ASSETTYPE
    VAL_ATTR = ASSETTYPE
    -> ArcStroker
swTreatmentDevice (reader GEODATABASE_SDE_1)
    attributes: OBJECTID integer, COMPKEY char(200), ASSETTYPE char(254), DESCR char(254), SERVSTAT char(254), OWN char(254), ZCOORD double, INVERTELEV double, DEVCAREA double, BARLDIAM double, BARLDIM2 double, DVCMATL char(254), CVRDIAM double, CVRTYPE char(254), MANUFCT char(20), INSTDATE char(20), ASBUILT char(30), SCHEME char(254), DATA_SRC char(50), COMMENTS char(254), ADDDBY char(20), ADDDTTM date, MODBY char(20), MODDTTM date, CONFIDENCE char(20), CRITICALITY double, ALLOCATE range_domain(ALLOCATE_5:integer:0:100), OLDGUID char(40), GlobalID globalid, created_user char(255),
      created_date date, last_edited_user char(255), last_edited_date date
    -> ArcStroker
swTreatmentDeviceArea (reader GEODATABASE_SDE_1) [off]
    attributes: OBJECTID integer, COMPKEYREF integer, COMMENTS char(254), ADDDBY char(20), ADDDTTM date, MODBY char(20), MODDTTM date, GlobalID globalid, created_user char(255), created_date date, last_edited_user char(255), last_edited_date date, SHAPE.STArea() double, SHAPE.STLength() double
    -> ArcStroker
wsMiscellaneous (reader GEODATABASE_SDE_1)
    attributes: OBJECTID integer, COMPKEY integer, ASSETTYPE char(254), DESCR char(254), SERVSTAT char(254), OWN char(254), ZCOORD double, INSTDATE date, ASBUILT char(30), SCHEME char(254), DATA_SRC char(20), COMMENTS char(254), ADDDBY char(20), ADDDTTM date, MODBY char(20), MODDTTM date, CONFIDENCE char(10), CRITICALITY double, ALLOCATE range_domain(ALLOCATE_4:integer:0:100), OLDGUID char(40), GlobalID globalid, created_user char(255), created_date date, last_edited_user char(255), last_edited_date date, SHAPE.STArea() double, SHAPE.STLength() double
    -> ArcStroker
wsTreatmentPlant (reader GEODATABASE_SDE_1)
    attributes: OBJECTID integer, COMPKEY integer, ASSETTYPE char(10), DESCR char(254), SERVSTAT char(254), OWN char(254), ZCOORD double, INSTDATE date, ASBUILT char(30), SCHEME char(254), DATA_SRC char(20), COMMENTS char(254), ADDDBY char(20), ADDDTTM date, MODBY char(20), MODDTTM date, CONFIDENCE char(10), CRITICALITY double, ALLOCATE range_domain(ALLOCATE_4:integer:0:100), OLDGUID char(40), created_user char(255), created_date date, last_edited_user char(255), last_edited_date date, GlobalID globalid, SHAPE.STArea() double, SHAPE.STLength() double
    -> ArcStroker
wwPumpStation (reader GEODATABASE_SDE_1)
    attributes: OBJECTID integer, COMPKEY integer, ASSETTYPE char(10), DESCR char(254), SERVSTAT char(10), OWN char(10), ZCOORD double, INSTDATE date, ASBUILT char(30), SCHEME char(50), DATA_SRC char(20), COMMENTS char(254), ADDDBY char(20), ADDDTTM date, MODBY char(20), MODDTTM date, CONFIDENCE char(20), CRITICALITY integer, ALLOCATE range_domain(ALLOCATE_4:integer:0:100), OLDGUID char(40), created_user char(255), created_date date, last_edited_user char(255), last_edited_date date, GlobalID globalid, SHAPE.STArea() double, SHAPE.STLength() double
    -> ArcStroker
wwTreatmentPlant (reader GEODATABASE_SDE_1)
    attributes: OBJECTID integer, COMPKEY integer, ASSETTYPE char(10), DESCR char(254), SERVSTAT char(254), OWN char(254), ZCOORD double, INSTDATE date, ASBUILT char(20), SCHEME char(254), DATA_SRC char(20), COMMENTS char(254), ADDDBY char(20), ADDDTTM date, MODBY char(20), MODDTTM date, CONFIDENCE char(20), CRITICALITY double, ALLOCATE range_domain(ALLOCATE_4:integer:0:100), OLDGUID char(40), created_user char(255), created_date date, last_edited_user char(255), last_edited_date date, GlobalID globalid, SHAPE.STArea() double, SHAPE.STLength() double
    -> ArcStroker
swMain (reader GEODATABASE_SDE_1)
    attributes: OBJECTID integer, COMPKEY integer, ASSETTYPE char(254), DESCR char(254), SERVSTAT char(254), OWN char(254), PIPEMATL char(254), PIPELEN double, NOMDIAM double, INTDIAM double, OUTDIAM double, UPNODE char(20), UPSELEV double, DWNNODE char(20), DWNELEV double, CLASS char(254), JTTYPE char(254), MANUFCT char(20), INSTMTHD char(254), INSTDATE date, LINEMATL char(254), LINEMTHD char(254), LINEDATE date, ASBUILT char(30), SCHEME char(254), DATA_SRC char(20), COMMENTS char(254), ADDDBY char(20), ADDDTTM date, MODBY char(20),
      MODDTTM date, CONFIDENCE char(10), CRITICALITY double, ALLOCATE range_domain(ALLOCATE_5:integer:0:100), OLDGUID char(40), GlobalID globalid, created_user char(255), created_date date, last_edited_user char(255), last_edited_date date, SHAPE.STLength() double
    -> ArcStroker
swChannel (reader GEODATABASE_SDE_1)
    attributes: OBJECTID integer, COMPKEY integer, ASSETTYPE char(254), DESCR char(254), SERVSTAT char(254), OWN char(254), CONMATL char(254), LENGTH double, TPWIDTH double, BSWIDTH double, CHDEPTH double, CHANSHAPE char(254), UPNODE char(20), UPSELEV double, DWNNODE char(20), DWNELEV double, INSTDATE date, ASBUILT char(30), SCHEME char(254), DATA_SRC char(20), COMMENTS char(254), ADDDBY char(20), ADDDTTM date, MODBY char(20), MODDTTM date, CONFIDENCE char(10), CRITICALITY double, ALLOCATE range_domain(ALLOCATE_5:integer:0:100), OLDGUID char(40), GlobalID globalid,
      created_user char(255), created_date date, last_edited_user char(255), last_edited_date date, SHAPE.STLength() double
    -> ArcStroker
swInlet (reader GEODATABASE_SDE_1)
    attributes: OBJECTID integer, COMPKEY integer, ASSETTYPE char(254), DESCR char(254), SERVSTAT char(254), OWN char(254), ZCOORD double, INVERTELEV double, MANUFCT char(20), INSTDATE date, ASBUILT char(30), SCHEME char(254), DATA_SRC char(20), COMMENTS char(254), ADDDBY char(20), ADDDTTM date, MODBY char(20), MODDTTM date, CONFIDENCE char(10), CRITICALITY double, ALLOCATE range_domain(ALLOCATE_5:integer:0:100), OLDGUID char(40), GlobalID globalid, created_user char(255), created_date date, last_edited_user char(255), last_edited_date date
    -> ArcStroker
swLateral (reader GEODATABASE_SDE_1)
    attributes: OBJECTID integer, COMPKEY integer, ASSETTYPE char(254), SRVTYPE char(254), DESCR char(254), SERVSTAT char(254), OWN char(254), PIPEMATL char(254), PIPELEN double, NOMDIAM double, INTDIAM double, OUTDIAM double, UPNODE char(20), UPSELEV double, DWNNODE char(20), DWNELEV double, CLASS char(254), JTTYPE char(254), MANUFCT char(20), INSTDATE date, ASBUILT char(30), SCHEME char(254), DATA_SRC char(20), COMMENTS char(254), ADDDBY char(20), ADDDTTM date, MODBY char(20), MODDTTM date, CONFIDENCE char(10), CRITICALITY double,
      ALLOCATE range_domain(ALLOCATE_5:integer:0:100), OLDGUID char(40), GlobalID globalid, created_user char(255), created_date date, last_edited_user char(255), last_edited_date date, SHAPE.STLength() double
    -> ArcStroker
swManhole (reader GEODATABASE_SDE_1)
    attributes: OBJECTID integer, COMPKEY integer, ASSETTYPE char(254), DESCR char(254), SERVSTAT char(254), OWN char(254), ZCOORD double, INVERTELEV double, BARLSHAPE char(254), BARLDIAM double, BARLDIM2 double, CHAMATL char(254), CVRDIAM double, CVRTYPE char(254), MANUFCT char(20), INSTDATE date, ASBUILT char(30), SCHEME char(254), DATA_SRC char(20), COMMENTS char(254), ADDDBY char(20), ADDDTTM date, MODBY char(20), MODDTTM date, CONFIDENCE char(10), CRITICALITY double, ALLOCATE range_domain(ALLOCATE_5:integer:0:100), OLDGUID char(40), GlobalID globalid, created_user char(255),
      created_date date, last_edited_user char(255), last_edited_date date
    -> ArcStroker
swMeter (reader GEODATABASE_SDE_1)
    attributes: OBJECTID integer, COMPKEY integer, ASSETTYPE char(20), DESCR char(254), SERVSTAT char(254), OWN char(254), ZCOORD double, INVERTELEV double, METERSZ double, SERNO char(20), MODELNO char(20), INSTDATE date, ASBUILT char(30), SCHEME char(50), DATA_SRC char(20), COMMENTS char(254), ADDDBY char(20), ADDDTTM date, MODBY char(20), MODDTTM date, CONFIDENCE char(10), CRITICALITY double, ALLOCATE range_domain(ALLOCATE_5:integer:0:100), GlobalID globalid, created_user char(255), created_date date, last_edited_user char(255), last_edited_date date
    -> ArcStroker
swNode (reader GEODATABASE_SDE_1)
    attributes: OBJECTID integer, COMPKEY integer, ASSETTYPE char(254), DESCR char(254), SERVSTAT char(254), OWN char(254), ZCOORD double, INVERTELEV double, INSTDATE date, ASBUILT char(30), SCHEME char(254), DATA_SRC char(20), COMMENTS char(254), ADDDBY char(20), ADDDTTM date, MODBY char(20), MODDTTM date, CONFIDENCE char(10), CRITICALITY double, ALLOCATE range_domain(ALLOCATE_5:integer:0:100), OLDGUID char(40), GlobalID globalid, created_user char(255), created_date date, last_edited_user char(255), last_edited_date date
    -> ArcStroker
swPumpstation (reader GEODATABASE_SDE_1)
    attributes: OBJECTID integer, COMPKEY integer, ASSETTYPE char(10), DESCR char(254), SERVSTAT char(254), OWN char(254), ZCOORD double, INSTDATE date, ASBUILT char(30), SCHEME char(254), DATA_SRC char(20), COMMENTS char(254), ADDDBY char(20), ADDDTTM date, MODBY char(20), MODDTTM date, CONFIDENCE char(20), CRITICALITY double, ALLOCATE range_domain(ALLOCATE_5:integer:0:100), GlobalID globalid, created_user char(255), created_date date, last_edited_user char(255), last_edited_date date, SHAPE.STArea() double, SHAPE.STLength() double
    -> ArcStroker
swStructure (reader GEODATABASE_SDE_1)
    attributes: OBJECTID integer, COMPKEY integer, ASSETTYPE char(254), DESCR char(254), SERVSTAT char(254), OWN char(254), ZCOORD double, MANUFCT char(20), INSTDATE date, ASBUILT char(30), SCHEME char(254), DATA_SRC char(20), COMMENTS char(254), ADDDBY char(20), ADDDTTM date, MODBY char(20), MODDTTM date, CONFIDENCE char(10), CRITICALITY double, ALLOCATE range_domain(ALLOCATE_5:integer:0:100), OLDGUID char(40), GlobalID globalid, created_user char(255), created_date date, last_edited_user char(255), last_edited_date date
    -> ArcStroker
swValve (reader GEODATABASE_SDE_1)
    attributes: OBJECTID integer, COMPKEY integer, ASSETTYPE char(10), DESCR char(254), SERVSTAT char(254), OWN char(254), ZCOORD double, INVERTELEV double, VALVESTAT char(254), VALVESZ double, SERNO char(20), MODELNO char(20), MANUFCT char(20), INSTDATE date, ASBUILT char(30), SCHEME char(254), DATA_SRC char(20), COMMENTS char(254), ADDDBY char(20), ADDDTTM date, MODBY char(20), MODDTTM date, CONFIDENCE char(10), CRITICALITY double, ALLOCATE range_domain(ALLOCATE_5:integer:0:100), OLDGUID char(40), GlobalID globalid, created_user char(255), created_date date, last_edited_user char(255),
      last_edited_date date
    -> ArcStroker
wsBackflow (reader GEODATABASE_SDE_1)
    attributes: OBJECTID integer, COMPKEY integer, ASSETTYPE char(254), DESCR char(254), SERVSTAT char(254), OWN char(254), ZCOORD double, INVERTELEV double, VALVESTAT char(254), VALVESZ double, SERNO char(20), MODELNO char(20), MANUFCT char(20), INSTDATE date, ASBUILT char(30), SCHEME char(254), DATA_SRC char(20), COMMENTS char(254), ADDDBY char(20), ADDDTTM date, MODBY char(20), MODDTTM date, CONFIDENCE char(10), CRITICALITY double, ALLOCATE range_domain(ALLOCATE_4:integer:0:100), OLDGUID char(40), GlobalID globalid, created_user char(255), created_date date, last_edited_user char(255),
      last_edited_date date
    -> ArcStroker
wsMain (reader GEODATABASE_SDE_1)
    attributes: OBJECTID integer, COMPKEY integer, ASSETTYPE char(254), DESCR char(254), SERVSTAT char(254), OWN char(254), PIPEMATL char(254), PIPELEN double, NOMDIAM double, INTDIAM double, OUTDIAM double, DPTH double, UPNODE char(50), DWNNODE char(50), CLASS char(254), JTTYPE char(254), MANUFCT char(20), INSTMTHD char(254), LINEMATL char(254), LINEMTHD char(254), LINEDATE date, INSTDATE date, ASBUILT char(30), SCHEME char(254), DATA_SRC char(20), COMMENTS char(254), ADDDBY char(20), ADDDTTM date, MODBY char(20), MODDTTM date,
      CONFIDENCE char(10), CRITICALITY double, ALLOCATE range_domain(ALLOCATE_4:integer:0:100), OLDGUID char(40), GlobalID globalid, created_user char(255), created_date date, last_edited_user char(255), last_edited_date date, SHAPE.STLength() double
    -> ArcStroker
wsMeter (reader GEODATABASE_SDE_1)
    attributes: OBJECTID integer, COMPKEY integer, ASSETTYPE char(254), DESCR char(254), SERVSTAT char(254), OWN char(254), ZCOORD double, INVERTELEV double, METERSZ double, SERNO char(20), MODELNO char(20), MANUFCT char(20), INSTDATE date, ASBUILT char(30), SCHEME char(254), DATA_SRC char(20), COMMENTS char(254), ADDDBY char(20), ADDDTTM date, MODBY char(20), MODDTTM date, CONFIDENCE char(10), CRITICALITY double, ALLOCATE range_domain(ALLOCATE_4:integer:0:100), OLDGUID char(40), GlobalID globalid, created_user char(255), created_date date, last_edited_user char(255), last_edited_date date
    -> ArcStroker
wsNode (reader GEODATABASE_SDE_1)
    attributes: OBJECTID integer, COMPKEY integer, ASSETTYPE char(254), DESCR char(254), SERVSTAT char(254), OWN char(254), ZCOORD double, INVERTELEV double, INSTDATE date, ASBUILT char(30), SCHEME char(254), DATA_SRC char(20), COMMENTS char(254), ADDDBY char(20), ADDDTTM date, MODBY char(20), MODDTTM date, CONFIDENCE char(10), CRITICALITY double, ALLOCATE range_domain(ALLOCATE_4:integer:0:100), OLDGUID char(40), GlobalID globalid, created_user char(255), created_date date, last_edited_user char(255), last_edited_date date
    -> ArcStroker
wsPumpStation (reader GEODATABASE_SDE_1)
    attributes: OBJECTID integer, COMPKEY integer, ASSETTYPE char(20), DESCR char(254), SERVSTAT char(254), OWN char(254), ZCOORD double, INSTDATE date, ASBUILT char(30), SCHEME char(254), DATA_SRC char(20), COMMENTS char(254), ADDDBY char(20), ADDDTTM date, MODBY char(20), MODDTTM date, CONFIDENCE char(10), CRITICALITY double, ALLOCATE range_domain(ALLOCATE_4:integer:0:100), OLDGUID char(40), created_user char(255), created_date date, last_edited_user char(255), last_edited_date date, GlobalID globalid, SHAPE.STArea() double, SHAPE.STLength() double
    -> ArcStroker
wsReservoir (reader GEODATABASE_SDE_1)
    attributes: OBJECTID integer, COMPKEY integer, ASSETTYPE char(10), DESCR char(254), SERVSTAT char(254), OWN char(254), ZCOORD double, INSTDATE date, ASBUILT char(30), SCHEME char(254), DATA_SRC char(20), COMMENTS char(254), ADDDBY char(20), ADDDTTM date, MODBY char(20), MODDTTM date, CONFIDENCE char(10), CRITICALITY double, ALLOCATE range_domain(ALLOCATE_4:integer:0:100), OLDGUID char(40), created_user char(255), created_date date, last_edited_user char(255), last_edited_date date, GlobalID globalid, SHAPE.STArea() double, SHAPE.STLength() double
    -> ArcStroker
wsValve (reader GEODATABASE_SDE_1)
    attributes: OBJECTID integer, COMPKEY integer, ASSETTYPE char(254), DESCR char(254), SERVSTAT char(254), OWN char(254), ZCOORD double, INVERTELEV double, VALVESTAT char(254), VALVESZ double, SERNO char(20), MODELNO char(20), MANUFCT char(20), INSTDATE date, ASBUILT char(30), SCHEME char(254), DATA_SRC char(20), COMMENTS char(254), ADDDBY char(20), ADDDTTM date, MODBY char(20), MODDTTM date, CONFIDENCE char(10), CRITICALITY double, ALLOCATE range_domain(ALLOCATE_4:integer:0:100), OLDGUID char(40), GlobalID globalid, created_user char(255), created_date date, last_edited_user char(255),
      last_edited_date date
    -> ArcStroker
wwLateral (reader GEODATABASE_SDE_1)
    attributes: OBJECTID integer, COMPKEY integer, ASSETTYPE char(254), SRVTYPE char(254), DESCR char(254), SERVSTAT char(254), OWN char(254), PIPEMATL char(254), PIPELEN double, NOMDIAM double, INTDIAM double, OUTDIAM double, CLASS char(254), MANUFCT char(20), INSTDATE date, ASBUILT char(30), SCHEME char(254), DATA_SRC char(20), COMMENTS char(254), ADDDBY char(20), ADDDTTM date, MODBY char(20), MODDTTM date, CONFIDENCE char(10), CRITICALITY double, ALLOCATE range_domain(ALLOCATE_4:integer:0:100), OLDGUID char(40), GlobalID globalid, created_user char(255), created_date date,
      last_edited_user char(255), last_edited_date date, SHAPE.STLength() double
    -> ArcStroker
wwManhole (reader GEODATABASE_SDE_1)
    attributes: OBJECTID integer, COMPKEY integer, ASSETTYPE char(254), SUBTYPE char(254), DESCR char(254), SERVSTAT char(254), OWN char(254), ZCOORD double, INVERTELEV double, BARLSHAPE char(254), BARLDIAM double, BARLDIM2 double, CHAMATL char(254), CVRDIAM double, CVRTYPE char(254), MANUFCT char(20), INSTDATE date, ASBUILT char(30), SCHEME char(254), DATA_SRC char(20), COMMENTS char(254), ADDDBY char(20), ADDDTTM date, MODBY char(20), MODDTTM date, CONFIDENCE char(10), CRITICALITY double, ALLOCATE range_domain(ALLOCATE_4:integer:0:100), OLDGUID char(40), GlobalID globalid,
      created_user char(255), created_date date, last_edited_user char(255), last_edited_date date
    -> ArcStroker
wwMeter (reader GEODATABASE_SDE_1)
    attributes: OBJECTID integer, COMPKEY integer, ASSETTYPE char(254), DESCR char(254), SERVSTAT char(254), OWN char(254), ZCOORD double, INVERTELEV double, METERSZ double, SERNO char(20), MODELNO char(20), MANUFCT char(20), INSTDATE date, ASBUILT char(30), SCHEME char(254), DATA_SRC char(20), COMMENTS char(254), ADDDBY char(20), ADDDTTM date, MODBY char(20), MODDTTM date, CONFIDENCE char(10), CRITICALITY double, ALLOCATE range_domain(ALLOCATE_4:integer:0:100), OLDGUID char(40), GlobalID globalid, created_user char(255), created_date date, last_edited_user char(255), last_edited_date date
    -> ArcStroker
wwNode (reader GEODATABASE_SDE_1)
    attributes: OBJECTID integer, COMPKEY integer, ASSETTYPE char(254), DESCR char(254), SERVSTAT char(254), OWN char(254), ZCOORD double, INVERTELEV double, INSTDATE date, ASBUILT char(30), SCHEME char(254), DATA_SRC char(20), COMMENTS char(254), ADDDBY char(20), ADDDTTM date, MODBY char(20), MODDTTM date, CONFIDENCE char(10), CRITICALITY double, ALLOCATE range_domain(ALLOCATE_4:integer:0:100), OLDGUID char(40), GlobalID globalid, created_user char(255), created_date date, last_edited_user char(255), last_edited_date date
    -> ArcStroker
wwValve (reader GEODATABASE_SDE_1)
    attributes: OBJECTID integer, COMPKEY integer, ASSETTYPE char(254), DESCR char(254), SERVSTAT char(254), OWN char(254), ZCOORD double, INVERTELEV double, VALVESTAT char(254), VALVESZ double, SERNO char(20), MODELNO char(20), MANUFCT char(20), INSTDATE date, ASBUILT char(30), SCHEME char(254), DATA_SRC char(20), COMMENTS char(254), ADDDBY char(20), ADDDTTM date, MODBY char(20), MODDTTM date, CONFIDENCE char(10), CRITICALITY double, ALLOCATE range_domain(ALLOCATE_4:integer:0:100), OLDGUID char(40), GlobalID globalid, created_user char(255), created_date date, last_edited_user char(255),
      last_edited_date date
    -> ArcStroker
ArcStroker
    MAKE_POLY = No
    STROKE_CHOICE = Maximum Deviation
    TOLERANCE_VAL = 0.1
    STROKED -> AttributeManager
AttributeManager
    ATTR_TABLE:
      SET_TO P_GUID = @Value(GlobalID)
      SET_TO MERGENAME = FME_CONDITIONAL:DEFAULT_VALUE'@Value(fme_feature_type)'BOOL_OP;OR;COMPOSITE_TEST;1;TEST @Value(ASSETTYPE) = CULVERT'SDE.swCulvert'FME_NUM_CONDITIONS2___
    -> FeatureTypeFilter
    -> SCHEME_Convert
SCHEME_Convert: AttributeValueMapper
    DEFAULT_VALUE = @Value(SCHEME)
    DIRECTION = Forward (Source To Destination)
    LUT = QUEENSTOWN,QUEENTWN,FRKN FLATS,FRNKFLAT,ARROWTOWN,ARRWTWN,GLENORCHY,GLENORCH,LAKE HAWEA,LKHAWEA,LAKE HAYES,LKHAYES,NO SCHEME,NOSCHEME,FME_NULL_VALUE,NOSCHEME,CARDRONA,CARDRONA,SHOTVR CTY,LKHAYES,ARTHURS PT,ARTHPT,ALBERT TN,WANAKA,SLOPEHILL,LKHAYES,KELVIN HTS,QUEENTWN,FERNHILL,QUEENTWN,BENDEMEER,NOSCHEME,MILLBROOK,NOSCHEME
    SRC = SCHEME
    VAL_ATTR = SCHEME
    -> CHAMATL_convert
CHAMATL_convert: AttributeValueMapper
    DEFAULT_VALUE = @Value(CHAMATL)
    DIRECTION = Forward (Source To Destination)
    LUT = CONC,CONCRETE,FIBREGLASS,FIBGLASS
    SRC = CHAMATL
    VAL_ATTR = CHAMATL
    -> ValveSTAT_convert
ValveSTAT_convert: AttributeValueMapper
    DEFAULT_VALUE = @Value(VALVESTAT)
    DIRECTION = Forward (Source To Destination)
    LUT = 0,CLOSED,Open,OPEN,Closed,CLOSED,1,OPEN,OPERATIVE,OPEN,UNKNOWN,FME_NULL_VALUE
    SRC = VALVESTAT
    VAL_ATTR = VALVESTAT
    -> MergeLayerAttributes [REQUESTOR]
FeatureTypeFilter [off]
    ATTRIBUTES = <Blank>,<Unfiltered>,SDE.swChannel,SDE.swInlet,SDE.swLateral,SDE.swMain,SDE.swManhole,SDE.swMeter,SDE.swNode,SDE.swPumpstation,SDE.swStructure,SDE.swTreatmentDevice,SDE.swTreatmentDeviceArea,SDE.swValve,SDE.wsBackflow,SDE.wsHydrant,SDE.wsLateral,SDE.wsMain,SDE.wsMeter,SDE.wsMiscellaneous,SDE.wsNode,SDE.wsPumpStation,SDE.wsReservoir,SDE.wsTreatmentPlant,SDE.wsValve,SDE.wwLateral,SDE.wwMain,SDE.wwManhole,SDE.wwMeter,SDE.wwNode,SDE.wwPumpStation,SDE.wwTreatmentPlant,SDE.wwValve
    SDE.swChannel -> FeatureWriter [SDE.swChannel]
    SDE.swInlet -> FeatureWriter [SDE.swInlet]
    SDE.swLateral -> FeatureWriter [SDE.swLateral]
    SDE.swMain -> AttributeFilter
    SDE.swManhole -> FeatureWriter [SDE.swManhole]
    SDE.swMeter -> FeatureWriter [SDE.swMeter]
    SDE.swNode -> FeatureWriter [SDE.swNode]
    SDE.swPumpstation -> FeatureWriter [SDE.swPumpstation]
    SDE.swStructure -> FeatureWriter [SDE.swStructure]
    SDE.swTreatmentDevice -> FeatureWriter [SDE.swTreatmentDevice]
    SDE.swValve -> FeatureWriter [SDE.swValve]
    SDE.wsBackflow -> FeatureWriter [SDE.wsBackflow]
    SDE.wsHydrant -> FeatureWriter [SDE.wsHydrant]
    SDE.wsLateral -> FeatureWriter [SDE.wsLateral]
    SDE.wsMain -> FeatureWriter [SDE.wsMain]
    SDE.wsMeter -> FeatureWriter [SDE.wsMeter]
    SDE.wsMiscellaneous -> FeatureWriter [SDE.wsMiscellaneous]
    SDE.wsNode -> FeatureWriter [SDE.wsNode]
    SDE.wsPumpStation -> FeatureWriter [SDE.wsPumpStation]
    SDE.wsReservoir -> FeatureWriter [FeatureClass1]
    SDE.wsTreatmentPlant -> FeatureWriter [SDE.wsTreatmentPlant]
    SDE.wsValve -> FeatureWriter [SDE.wsValve]
    SDE.wwLateral -> FeatureWriter [SDE.wwLateral]
    SDE.wwMain -> FeatureWriter [SDE.wwMain]
    SDE.wwManhole -> FeatureWriter [SDE.wwManhole]
    SDE.wwMeter -> FeatureWriter [SDE.wwMeter]
    SDE.wwNode -> FeatureWriter [SDE.wwNode]
    SDE.wwPumpStation -> FeatureWriter [SDE.wwPumpStation]
    SDE.wwTreatmentPlant -> FeatureWriter [SDE.wwTreatmentPlant]
    SDE.wwValve -> FeatureWriter [SDE.wwValve]
AttributeFilter [off]
    ATTR_NAME = ASSETTYPE
    ATTR_VALUES = <Empty>,<Missing>,<Null>,<Unfiltered>,CULVERT
    <UNFILTERED> -> FeatureWriter [SDE.swMain]
    CULVERT -> FeatureWriter [CULVERT]
FeatureWriter [off]
    DATASET = $(FME_MF_DIR_ENCODED)TechOneFormats\FGDB_ChangesOnly.gdb
    DATASET_ATTR = _dataset
    FEATURE_TYPE_LIST_ATTR = _feature_type
    FORMAT = GEODATABASE_FILE
    GEODATABASE_FILE_ANNOTATION_UNITS = unknown_units
    GEODATABASE_FILE_COMPRESS_AT_END = no
    GEODATABASE_FILE_COORDINATE_SYSTEM_GRANULARITY = FEATURE_TYPE
    GEODATABASE_FILE_DEFAULT_Z_VALUE = 0
    GEODATABASE_FILE_DESTINATION_DATASETTYPE_VALIDATION = Yes
    GEODATABASE_FILE_DUMP_FAILED_FEATURES = no
    GEODATABASE_FILE_ENABLE_FAST_DELETES = yes
    GEODATABASE_FILE_GRID_1 = 0
    GEODATABASE_FILE_HAS_MEASURES = no
    GEODATABASE_FILE_HAS_Z_VALUES = auto_detect
    GEODATABASE_FILE_IGNORE_FAILED_FEATURE_ENTRY = no
    GEODATABASE_FILE_MAX_NUMBER_FAILED_FEATURES = -1
    GEODATABASE_FILE_OVERWRITE_GEODB = YES
    GEODATABASE_FILE_REQUESTED_GEODATABASE_VERSION = CURRENT
    GEODATABASE_FILE_SIMPLIFY_GEOM = No
    GEODATABASE_FILE_SIMPLIFY_NETWORK_FEATURES = no
    GEODATABASE_FILE_TRANSACTION = 0
    GEODATABASE_FILE_TRANSACTION_INTERVAL = 1000
    GEODATABASE_FILE_TRANSACTION_TYPE = TRANSACTIONS
    GEODATABASE_FILE_VALIDATE_FEATURES = no
    GEODATABASE_FILE_XY_SCALE = 0
    GEODATABASE_FILE_X_ORIGIN = 0
    GEODATABASE_FILE_Y_ORIGIN = 0
    GEODATABASE_FILE_Z_ORIGIN = 0
    GEODATABASE_FILE_Z_SCALE = 0
    TOTAL_FEATURES_WRITTEN_ATTR = _total_features_written
    SDE.swChannel -> MergeLayerAttributes [REQUESTOR]
    SDE.swInlet -> MergeLayerAttributes [REQUESTOR]
    SDE.swLateral -> MergeLayerAttributes [REQUESTOR]
    SDE.swMain -> MergeLayerAttributes [REQUESTOR]
    CULVERT -> MergeLayerAttributes [REQUESTOR]
    SDE.swManhole -> MergeLayerAttributes [REQUESTOR]
    SDE.swMeter -> MergeLayerAttributes [REQUESTOR]
    SDE.swNode -> MergeLayerAttributes [REQUESTOR]
    SDE.swPumpstation -> MergeLayerAttributes [REQUESTOR]
    SDE.swStructure -> MergeLayerAttributes [REQUESTOR]
    SDE.swTreatmentDevice -> MergeLayerAttributes [REQUESTOR]
    SDE.swValve -> MergeLayerAttributes [REQUESTOR]
    SDE.wsBackflow -> MergeLayerAttributes [REQUESTOR]
    SDE.wsHydrant -> MergeLayerAttributes [REQUESTOR]
    SDE.wsLateral -> MergeLayerAttributes [REQUESTOR]
    SDE.wsMain -> MergeLayerAttributes [REQUESTOR]
    SDE.wsMeter -> MergeLayerAttributes [REQUESTOR]
    SDE.wsMiscellaneous -> MergeLayerAttributes [REQUESTOR]
    SDE.wsNode -> MergeLayerAttributes [REQUESTOR]
    SDE.wsPumpStation -> MergeLayerAttributes [REQUESTOR]
    SDE.wsTreatmentPlant -> MergeLayerAttributes [REQUESTOR]
    FeatureClass1 -> MergeLayerAttributes [REQUESTOR]
    SDE.wsValve -> MergeLayerAttributes [REQUESTOR]
    SDE.wwLateral -> MergeLayerAttributes [REQUESTOR]
    SDE.wwMain -> MergeLayerAttributes [REQUESTOR]
    SDE.wwManhole -> MergeLayerAttributes [REQUESTOR]
    SDE.wwMeter -> MergeLayerAttributes [REQUESTOR]
    SDE.wwNode -> MergeLayerAttributes [REQUESTOR]
    SDE.wwPumpStation -> MergeLayerAttributes [REQUESTOR]
    SDE.wwTreatmentPlant -> MergeLayerAttributes [REQUESTOR]
    SDE.wwValve -> MergeLayerAttributes [REQUESTOR]
Note: Need to change the interceptor gislayer template in techone spatial configuration
Note: Double check that swCulvert is a featuretype now
GISID_ASSETNUMBER_MATCH (reader CSV2_2)
    attributes: Asset string, GIS_ID string
    -> FeatureMerger [REQUESTOR]
    -> AssetNumberAdder [SUPPLIER]
Note: Remove me after adding new global ids to techone
GlobalIDMatch (reader CSV2_3) [off]
    attributes: OLDGlobalID string, NEWGlobalID string
    -> FeatureMerger [SUPPLIER]
FeatureMerger [off]
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = @Value(GIS_ID) @Value(OLDGlobalID) AUTO
    MERGE_TYPE = Attributes Only
    PROCESS_DUPS = YES
    REJECT_NULL_MISSING_KEYS = No
    SUPPLIERS_FIRST = No
    MERGED -> AssetNumberAdder [SUPPLIER]
    UNMERGED_REQUESTOR -> AttributeManager_3
AttributeManager_3 [off]
    ATTR_TABLE = RENAME_SET_VALUE GIS_ID > NEWGlobalID
    -> AssetNumberAdder [SUPPLIER]
AssetNumberAdder: FeatureMerger
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = @Value(P_GUID) @Value(GIS_ID) AUTO
    MERGE_TYPE = Attributes Only
    PROCESS_DUPS = YES
    REJECT_NULL_MISSING_KEYS = No
    SUPPLIERS_FIRST = No
    MERGED -> CSV_Field_Creator_TechOne
    UNMERGED_REQUESTOR -> CSV_Field_Creator_TechOne
Note: Fix all references to fix
CSV_Field_Creator_TechOne: AttributeManager
    ATTR_TABLE:
      SET_TO AssetNumber = @Value(Asset)
      RENAME_SET_VALUE COMPKEY > OtherNumber
      RENAME_SET_VALUE P_GUID > GisId
      RENAME_SET_VALUE SERNO > SerialNumber
      RENAME_SET_VALUE MODELNO > ModelNumber
      RENAME_SET_VALUE NewLayerName > GisLayer
      RENAME_SET_VALUE OWN > RegisterSelectionType2
      RENAME_SET_VALUE SERVSTAT > RegisterSelectionType3
      RENAME_SET_VALUE SCHEME > RegisterUserfield1
      RENAME_SET_VALUE ASBUILT > RegisterUserfield2
      SET_TO Details = FME_CONDITIONAL:DEFAULT_VALUE'@Value(FriendlyCompDesc) [@Value(OtherNumber)] UNITTYPE [@Value(ASSETTYPE)]'BOOL_OP;OR;COMPOSITE_TEST;1;TEST @Value(fme_feature_type) IN SDE.wsReservoir,SDE.wsPumpStation,SDE.wsTreatmentPlant,SDE.swPumpstation,SDE.wwPumpStation,SDE.wwTreatmentPlant'@Value(DESCR)-@Value(FriendlyCompDesc) [@Value(OtherNumber)] UNITTYPE [@Value(ASSETTYPE)]'FME_NUM_CONDITIONS2___
      SET_TO Description = @Value(FriendlyCompDesc) [@Value(OtherNumber)]
      SET_TO ShortDescription = @Value(FriendlyCompDesc)
      SET_TO AcquisitionDate = @DateTimeFormat(@Value(INSTDATE),%d/%m/%Y)
      SET_TO OperatingStatus = FME_CONDITIONAL:DEFAULT_VALUE'O'BOOL_OP;OR;COMPOSITE_TEST;1;TEST @Value(RegisterSelectionType3) = ACTIVE'I'FME_NUM_CONDITIONS2___
      SET_TO PrimaryDimension = FME_CONDITIONAL:DEFAULT_VALUE'1'BOOL_OP;OR;COMPOSITE_TEST;1;TEST @Value(fme_feature_type) = SDE.swChannel'@Value(LENGTH)'BOOL_OP;OR;COMPOSITE_TEST;1;TEST @Value(fme_feature_type) IN SDE.wsMain,SDE.wsLateral,SDE.wwMain,SDE.wwLateral,SDE.swMain,SDE.swLateral'@Value(PIPELEN)'FME_NUM_CONDITIONS3___
      SET_TO AssetAttributeSelectionType1-Level2 = FME_CONDITIONAL:DEFAULT_VALUE'_FME_NO_OP_'BOOL_OP;OR;COMPOSITE_TEST;1;TEST @Value(fme_feature_type) IN SDE.swPumpstation,SDE.wsPumpstation,SDE.wwPumpstation,SDE.wwTreatmentPlant,SDE.wsTreatmentPlant,SDE.wsReservoir'@Value(ASSETTYPE)'FME_NUM_CONDITIONS2___
      SET_TO AssetAttributeSelectionType1-Level3 = FME_CONDITIONAL:DEFAULT_VALUE'_FME_NO_OP_'BOOL_OP;OR;COMPOSITE_TEST;1;TEST @Value(fme_feature_type) IN SDE.wsMain,SDE.wsLateral,SDE.swChannel,SDE.swMain,SDE.swStorageBasin,SDE.wwMain,SDE.wwLateral,SDE.wwNode,SDE.wwManhole,SDE.wsBackflow,SDE.wsHydrant,SDE.wsNode'@Value(ASSETTYPE)'FME_NUM_CONDITIONS2___
      SET_TO AssetAttributeSelectionType2-Level3 = FME_CONDITIONAL:DEFAULT_VALUE'_FME_NO_OP_'BOOL_OP;OR;COMPOSITE_TEST;1;TEST @Value(fme_feature_type) = SDE.wwManhole'@Value(CVRTYPE)'BOOL_OP;OR;COMPOSITE_TEST;1;TEST @Value(fme_feature_type) IN SDE.wsValve,SDE.wwValve'@Value(ASSETTYPE)'BOOL_OP;OR;COMPOSITE_TEST;1;TEST @Value(fme_feature_type) = SDE.swChannel'@Value(CHANSHAPE)'FME_NUM_CONDITIONS4___
      SET_TO AssetAttributeSelectionType3-Level3 = FME_CONDITIONAL:DEFAULT_VALUE'_FME_NO_OP_'BOOL_OP;OR;COMPOSITE_TEST;1;TEST @Value(fme_feature_type) IN SDE.wwLateral,SDE.wwMain,SDE.wsMain,SDE.wsLateral,SDE.swMain,SDE.swLateral'@Value(PIPEMATL)'BOOL_OP;OR;COMPOSITE_TEST;1;TEST @Value(fme_feature_type) IN SDE.wsBackflow,SDE.wwValve,SDE.wsValve'@Value(VALVESTAT)'BOOL_OP;OR;COMPOSITE_TEST;1;TEST @Value(fme_feature_type) = SDE.swChannel'@Value(CONMATL)'FME_NUM_CONDITIONS4___
      SET_TO AssetAttributeSelectionType4-Level3 = @Value(CLASS)
      SET_TO AssetAttributeSelectionType5-Level3 = FME_CONDITIONAL:DEFAULT_VALUE'_FME_NO_OP_'BOOL_OP;OR;COMPOSITE_TEST;1;TEST @Value(fme_feature_type) IN SDE.swMain,SDE.wwMain,SDE.wsMain'@Value(JTTYPE)'FME_NUM_CONDITIONS2___
      SET_TO AssetAttributeSelectionType7-Level3 = FME_CONDITIONAL:DEFAULT_VALUE'_FME_NO_OP_'BOOL_OP;OR;COMPOSITE_TEST;1;TEST @Value(fme_feature_type) = SDE.wwManhole'@Value(CHAMATL)'FME_NUM_CONDITIONS2___
      SET_TO AssetAttributeSelectionType9-Level3 = @Value(SRVTYPE)
      SET_TO AssetAttributeUserfield1-Level3 = FME_CONDITIONAL:DEFAULT_VALUE'@Value(PIPELEN)'BOOL_OP;OR;COMPOSITE_TEST;1;TEST @Value(fme_feature_type) = SDE.swChannel'@Value(LENGTH)'BOOL_OP;OR;COMPOSITE_TEST;1;TEST @Value(fme_feature_type) IN SDE.wwMeter,SDE.wsMeter'@Value(METERSZ)'BOOL_OP;OR;COMPOSITE_TEST;1;TEST @Value(fme_feature_type) = SDE.wsBackflow'@Value(VALVESZ)'FME_NUM_CONDITIONS4___
      SET_TO AssetAttributeUserfield2-Level3 = @Value(NOMDIAM)
      SET_TO AssetAttributeUserfield3-Level3 = FME_CONDITIONAL:DEFAULT_VALUE'_FME_NO_OP_'BOOL_OP;OR;COMPOSITE_TEST;1;TEST @Value(fme_feature_type) IN SDE.wwValve,SDE.wsValve'@Value(VALVESZ)'FME_NUM_CONDITIONS2___
      SET_TO AssetAttributeUserfield4-Level3 = FME_CONDITIONAL:DEFAULT_VALUE'_FME_NO_OP_'BOOL_OP;OR;COMPOSITE_TEST;1;TEST @Value(fme_feature_type) IN SDE.swChannel,SDE.swCulvert,SDE.swMain,SDE.wwMain'@Value(UPSELEV)'BOOL_OP;OR;COMPOSITE_TEST;1;TEST @Value(fme_feature_type) IN SDE.wsNode,SDE.wsValve'@Value(INVERTELEV)'FME_NUM_CONDITIONS3___
      SET_TO AssetAttributeUserfield5-Level3 = FME_CONDITIONAL:DEFAULT_VALUE'_FME_NO_OP_'BOOL_OP;OR;COMPOSITE_TEST;1;TEST @Value(fme_feature_type) IN SDE.swChannel,SDE.swCulvert,SDE.swMain,SDE.wwMain'@Value(DWNELEV)'FME_NUM_CONDITIONS2___
      SET_TO AssetAttributeUserfield9-Level3 = FME_CONDITIONAL:DEFAULT_VALUE'_FME_NO_OP_'BOOL_OP;OR;COMPOSITE_TEST;1;TEST @Value(fme_feature_type) != SDE.swManhole'@Value(BARLDIAM)'FME_NUM_CONDITIONS2___
      SET_TO AssetAttributeUserfield10-Level3 = FME_CONDITIONAL:DEFAULT_VALUE'_FME_NO_OP_'BOOL_OP;OR;COMPOSITE_TEST;1;TEST @Value(fme_feature_type) IN SDE.wsHydrant,SDE.wsMeter,SDE.wsNode,SDE.wsValve'@Value(ZCOORD)'FME_NUM_CONDITIONS2___
      SET_TO AssetAttributeUserfield12-Level3 = FME_CONDITIONAL:DEFAULT_VALUE'_FME_NO_OP_'BOOL_OP;OR;COMPOSITE_TEST;1;TEST @Value(fme_feature_type) IN SDE.wwManhole,SDE.wwNode,SDE.wwValve'@Value(INVERTELEV)'FME_NUM_CONDITIONS2___
      SET_TO AssetAttributeUserfield13-Level3 = FME_CONDITIONAL:DEFAULT_VALUE'_FME_NO_OP_'BOOL_OP;OR;COMPOSITE_TEST;1;TEST @Value(fme_feature_type) = SDE.wwManhole'@Value(CVRDIAM)'FME_NUM_CONDITIONS2___
      SET_TO AssetAttributeUserfield14-Level3 = FME_CONDITIONAL:DEFAULT_VALUE'_FME_NO_OP_'BOOL_OP;OR;COMPOSITE_TEST;1;TEST @Value(fme_feature_type) IN SDE.wwManhole,SDE.wwNode,SDE.wwValve,SDE.wwMeter'@Value(ZCOORD)'FME_NUM_CONDITIONS2___
      SET_TO AssetAttributeSelectionType1-Level4 = FME_CONDITIONAL:DEFAULT_VALUE'_FME_NO_OP_'BOOL_OP;OR;COMPOSITE_TEST;1;TEST @Value(fme_feature_type) IN SDE.swManhole,SDE.swMeter,SDE.swNode,SDE.swInlet,SDE.wsMiscellaneous'@Value(ASSETTYPE)'FME_NUM_CONDITIONS2___
      SET_TO AssetAttributeSelectionType2-Level4 = FME_CONDITIONAL:DEFAULT_VALUE'_FME_NO_OP_'BOOL_OP;OR;COMPOSITE_TEST;1;TEST @Value(fme_feature_type) = SDE.swManhole'@Value(CVRTYPE)'BOOL_OP;OR;COMPOSITE_TEST;1;TEST @Value(fme_feature_type) = SDE.swValve'@Value(ASSETTYPE)'FME_NUM_CONDITIONS3___
      SET_TO AssetAttributeSelectionType3-Level4 = FME_CONDITIONAL:DEFAULT_VALUE'_FME_NO_OP_'BOOL_OP;OR;COMPOSITE_TEST;1;TEST @Value(fme_feature_type) = SDE.swValve'@Value(VALVESTAT)'FME_NUM_CONDITIONS2___
      SET_TO AssetAttributeSelectionType7-Level4 = FME_CONDITIONAL:DEFAULT_VALUE'_FME_NO_OP_'BOOL_OP;OR;COMPOSITE_TEST;1;TEST @Value(fme_feature_type) = SDE.swManhole'@Value(CHAMATL)'FME_NUM_CONDITIONS2___
      SET_TO AssetAttributeSelectionType11-Level4 = FME_CONDITIONAL:DEFAULT_VALUE'_FME_NO_OP_'BOOL_OP;OR;COMPOSITE_TEST;1;TEST @Value(fme_feature_type) = SDE.swStructure'@Value(ASSETTYPE)'FME_NUM_CONDITIONS2___
      SET_TO AssetAttributeUserfield3-Level4 = FME_CONDITIONAL:DEFAULT_VALUE'_FME_NO_OP_'BOOL_OP;OR;COMPOSITE_TEST;1;TEST @Value(fme_feature_type) = SDE.swValve'@Value(VALVESZ)'FME_NUM_CONDITIONS2___
      SET_TO AssetAttributeUserfield5-Level4 = FME_CONDITIONAL:DEFAULT_VALUE'_FME_NO_OP_'BOOL_OP;OR;COMPOSITE_TEST;1;TEST @Value(fme_feature_type) = SDE.wsMiscellaneous'@Value(ZCOORD)'FME_NUM_CONDITIONS2___
      SET_TO AssetAttributeUserfield9-Level4 = FME_CONDITIONAL:DEFAULT_VALUE'_FME_NO_OP_'BOOL_OP;OR;COMPOSITE_TEST;1;TEST @Value(fme_feature_type) = SDE.swManhole'@Value(BARLDIAM)'FME_NUM_CONDITIONS2___
      SET_TO AssetAttributeUserfield11-Level4 = FME_CONDITIONAL:DEFAULT_VALUE'_FME_NO_OP_'BOOL_OP;OR;COMPOSITE_TEST;1;TEST @Value(fme_feature_type) IN SDE.swManhole,SDE.swNode,SDE.swValve'@Value(INVERTELEV)'FME_NUM_CONDITIONS2___
      SET_TO AssetAttributeUserfield13-Level4 = FME_CONDITIONAL:DEFAULT_VALUE'_FME_NO_OP_'BOOL_OP;OR;COMPOSITE_TEST;1;TEST @Value(fme_feature_type) = SDE.swManhole'@Value(CVRDIAM)'FME_NUM_CONDITIONS2___
      SET_TO AssetAttributeUserfield15-Level4 = FME_CONDITIONAL:DEFAULT_VALUE'_FME_NO_OP_'BOOL_OP;OR;COMPOSITE_TEST;1;TEST @Value(fme_feature_type) IN SDE.swManhole,SDE.swNode,SDE.swInlet,SDE.swValve'@Value(ZCOORD)'FME_NUM_CONDITIONS2___
      RENAME_SET_VALUE MANUFCT > ManufacturerName
    -> RegisterLevelAttributes
    -> AssetAttributesLevel1
    -> AssetAttributesLevel2
    -> AssetAttributesLevel3
    -> AssetAttributesLevel4
RegisterLevelAttributes: AttributeManager
    ATTR_TABLE:
      SET_TO AssetRegisterName = ALM_REG1
      SET_TO LineType = ASSET
      SET_TO TemplateAssetNumber = FME_CONDITIONAL:DEFAULT_VALUE'_FME_NO_OP_'BOOL_OP;OR;COMPOSITE_TEST;1;TEST AssetNumber ATTRIBUTE_HAS_A_VALUE _FME_BLANK_STRING_'FME_NULL_VALUE'FME_NUM_CONDITIONS2___
      SET_TO
      SET_TO
      SET_TO Status = N
      REMOVE OBJECTID
      REMOVE ZCOORD
      REMOVE INSTDATE
      REMOVE UNITTYPE
      REMOVE ADDDBY
      REMOVE ADDDTTM
      REMOVE MODBY
      REMOVE MODDTTM
      REMOVE CONFIDENCE
      REMOVE DATA_SRC
      REMOVE COMMENTS
      REMOVE GlobalID
      REMOVE VALVESZ
      REMOVE VALVESTAT
      REMOVE INVERTELEV
      REMOVE PIPELEN
      REMOVE SRVTYPE
      REMOVE CLASS
      REMOVE UPSELEV
      REMOVE DWNELEV
      REMOVE LENGTH
      REMOVE CONMATL
      REMOVE CHANSHAPE
      REMOVE fme_feature_type
      REMOVE JTTYPE
      REMOVE DPTH
      REMOVE METERSZ
      REMOVE CVRDIAM
      REMOVE BARLDIAM
      REMOVE CVRTYPE
      REMOVE FriendlyCompDesc
      REMOVE LAYER_NETWORK_TYPE
      REMOVE ASSET_TYPE_LEVELS
      REMOVE AssetAttributeSelectionType1-Level2
      REMOVE AssetAttributeSelectionType1-Level3
      REMOVE AssetAttributeSelectionType2-Level3
      REMOVE AssetAttributeSelectionType3-Level3
      REMOVE AssetAttributeSelectionType4-Level3
      REMOVE AssetAttributeSelectionType5-Level3
      REMOVE AssetAttributeSelectionType7-Level3
      REMOVE AssetAttributeSelectionType9-Level3
      REMOVE AssetAttributeUserfield1-Level3
      REMOVE AssetAttributeUserfield2-Level3
      REMOVE AssetAttributeUserfield3-Level3
      REMOVE AssetAttributeUserfield4-Level3
      REMOVE AssetAttributeUserfield5-Level3
      REMOVE AssetAttributeUserfield9-Level3
      REMOVE AssetAttributeUserfield10-Level3
      REMOVE AssetAttributeUserfield12-Level3
      REMOVE AssetAttributeUserfield13-Level3
      REMOVE AssetAttributeUserfield14-Level3
      REMOVE AssetAttributeSelectionType1-Level4
      REMOVE AssetAttributeSelectionType2-Level4
      REMOVE AssetAttributeSelectionType3-Level4
      REMOVE AssetAttributeSelectionType7-Level4
      REMOVE AssetAttributeSelectionType11-Level4
      REMOVE AssetAttributeUserfield3-Level4
      REMOVE AssetAttributeUserfield5-Level4
      REMOVE AssetAttributeUserfield9-Level4
      REMOVE AssetAttributeUserfield11-Level4
      REMOVE AssetAttributeUserfield13-Level4
      REMOVE AssetAttributeUserfield15-Level4
      REMOVE GIS_ID
      REMOVE fme_dataset
      SET_TO IgnoreAuditing = FALSE
      SET_TO Type = S
      SET_TO FunctionSelectionCode = TBD
      SET_TO CapacitySelectionCode = TBD
      SET_TO UtilisationSelectionCode = TBD
      SET_TO RiskConsequenceSelectionCode = TBD
      SET_TO IsAvailableForDepreciationProcessing = TRUE
      REMOVE ASSETTYPE
      REMOVE DESCR
      RENAME_SET_VALUE CRITICALITY > CriticalitySelectionCode = FME_CONDITIONAL:DEFAULT_VALUE'_FME_NO_OP_'BOOL_OP;OR;COMPOSITE_TEST;1;TEST @Value(CriticalitySelectionCode) = 5'4'BOOL_OP;OR;COMPOSITE_TEST;1;TEST CriticalitySelectionCode ATTRIBUTE_VALUE_NULL _FME_BLANK_STRING_'TBD'FME_NUM_CONDITIONS3___
      REMOVE ALLOCATE
      REMOVE OLDGUID
      REMOVE created_user
      REMOVE created_date
      REMOVE last_edited_user
      REMOVE last_edited_date
      REMOVE SHAPE.STArea()
      REMOVE SHAPE.STLength()
      REMOVE SUBTYPE
      REMOVE BARLSHAPE
      REMOVE BARLDIM2
      REMOVE CHAMATL
      REMOVE TPWIDTH
      REMOVE BSWIDTH
      REMOVE CHDEPTH
      REMOVE UPNODE
      REMOVE DWNNODE
      REMOVE PIPEMATL
      REMOVE NOMDIAM
      REMOVE INTDIAM
      REMOVE OUTDIAM
      REMOVE INSTMTHD
      REMOVE LINEMATL
      REMOVE LINEMTHD
      REMOVE LINEDATE
      REMOVE COMPKEYREF
      REMOVE DEVCAREA
      REMOVE DVCMATL
    -> FinalFieldNames
AssetAttributesLevel1: AttributeManager
    ATTR_TABLE:
      REMOVE OBJECTID
      SET_TO LineType = ATTRIBUTE
      SET_TO
      SET_TO AttributeCode = ASSET_TYPE
      SET_TO LevelNumber = 1
      REMOVE ZCOORD
      REMOVE INSTDATE
      REMOVE UNITTYPE
      REMOVE ADDDBY
      REMOVE ADDDTTM
      REMOVE MODBY
      REMOVE MODDTTM
      REMOVE CONFIDENCE
      REMOVE OtherNumber
      REMOVE DATA_SRC
      REMOVE COMMENTS
      REMOVE GlobalID
      REMOVE SerialNumber
      REMOVE VALVESZ
      REMOVE ModelNumber
      REMOVE VALVESTAT
      REMOVE ManufacturerName
      REMOVE INVERTELEV
      REMOVE PIPELEN
      REMOVE SRVTYPE
      REMOVE CLASS
      REMOVE UPSELEV
      REMOVE DWNELEV
      REMOVE LENGTH
      REMOVE CONMATL
      REMOVE CHANSHAPE
      REMOVE fme_feature_type
      REMOVE JTTYPE
      REMOVE DPTH
      REMOVE METERSZ
      REMOVE CVRDIAM
      REMOVE BARLDIAM
      REMOVE CVRTYPE
      REMOVE GisLayer
      REMOVE FriendlyCompDesc
      REMOVE LAYER_NETWORK_TYPE
      REMOVE ASSET_TYPE_LEVELS
      REMOVE RegisterSelectionType2
      REMOVE RegisterSelectionType3
      REMOVE RegisterUserfield1
      REMOVE RegisterUserfield2
      REMOVE Details
      REMOVE Description
      REMOVE ShortDescription
      REMOVE AcquisitionDate
      REMOVE OperatingStatus
      REMOVE PrimaryDimension
      REMOVE TemplateAssetNumber
      REMOVE PrimaryDimensionUnitOfMeasure
      REMOVE AssetAttributeSelectionType1-Level2
      REMOVE AssetAttributeSelectionType1-Level3
      REMOVE AssetAttributeSelectionType2-Level3
      REMOVE AssetAttributeSelectionType3-Level3
      REMOVE AssetAttributeSelectionType4-Level3
      REMOVE AssetAttributeSelectionType5-Level3
      REMOVE AssetAttributeSelectionType7-Level3
      REMOVE AssetAttributeSelectionType9-Level3
      REMOVE AssetAttributeUserfield1-Level3
      REMOVE AssetAttributeUserfield2-Level3
      REMOVE AssetAttributeUserfield3-Level3
      REMOVE AssetAttributeUserfield4-Level3
      REMOVE AssetAttributeUserfield5-Level3
      REMOVE AssetAttributeUserfield9-Level3
      REMOVE AssetAttributeUserfield10-Level3
      REMOVE AssetAttributeUserfield12-Level3
      REMOVE AssetAttributeUserfield13-Level3
      REMOVE AssetAttributeUserfield14-Level3
      REMOVE AssetAttributeSelectionType1-Level4
      REMOVE AssetAttributeSelectionType2-Level4
      REMOVE AssetAttributeSelectionType3-Level4
      REMOVE AssetAttributeSelectionType7-Level4
      REMOVE AssetAttributeSelectionType11-Level4
      REMOVE AssetAttributeUserfield3-Level4
      REMOVE AssetAttributeUserfield5-Level4
      REMOVE AssetAttributeUserfield9-Level4
      REMOVE AssetAttributeUserfield11-Level4
      REMOVE AssetAttributeUserfield13-Level4
      REMOVE AssetAttributeUserfield15-Level4
      REMOVE AssetNumber
      REMOVE Asset
      REMOVE GIS_ID
      REMOVE fme_dataset
      REMOVE ASSETTYPE
      REMOVE DESCR
      REMOVE CRITICALITY
      REMOVE ALLOCATE
      REMOVE OLDGUID
      REMOVE created_user
      REMOVE created_date
      REMOVE last_edited_user
      REMOVE last_edited_date
      REMOVE SHAPE.STArea()
      REMOVE SHAPE.STLength()
      REMOVE SUBTYPE
      REMOVE BARLSHAPE
      REMOVE BARLDIM2
      REMOVE CHAMATL
      REMOVE TPWIDTH
      REMOVE BSWIDTH
      REMOVE CHDEPTH
      REMOVE UPNODE
      REMOVE DWNNODE
      REMOVE PIPEMATL
      REMOVE NOMDIAM
      REMOVE INTDIAM
      REMOVE OUTDIAM
      REMOVE INSTMTHD
      REMOVE LINEMATL
      REMOVE LINEMTHD
      REMOVE LINEDATE
      REMOVE COMPKEYREF
      REMOVE DEVCAREA
      REMOVE DVCMATL
    -> FinalFieldNames
AssetAttributesLevel2: AttributeManager
    ATTR_TABLE:
      REMOVE OBJECTID
      SET_TO LineType = ATTRIBUTE
      SET_TO AttributeCode = ASSET_TYPE
      SET_TO LevelNumber = 2
      REMOVE AssetNumber
      REMOVE ZCOORD
      REMOVE INSTDATE
      REMOVE UNITTYPE
      REMOVE ADDDBY
      REMOVE ADDDTTM
      REMOVE MODBY
      REMOVE MODDTTM
      REMOVE CONFIDENCE
      REMOVE OtherNumber
      REMOVE DATA_SRC
      REMOVE COMMENTS
      REMOVE GlobalID
      REMOVE SerialNumber
      REMOVE VALVESZ
      REMOVE ModelNumber
      REMOVE VALVESTAT
      REMOVE ManufacturerName
      REMOVE INVERTELEV
      REMOVE PIPELEN
      REMOVE SRVTYPE
      REMOVE CLASS
      REMOVE UPSELEV
      REMOVE DWNELEV
      REMOVE LENGTH
      REMOVE CONMATL
      REMOVE CHANSHAPE
      REMOVE fme_feature_type
      REMOVE JTTYPE
      REMOVE DPTH
      REMOVE METERSZ
      REMOVE CVRDIAM
      REMOVE BARLDIAM
      REMOVE CVRTYPE
      REMOVE GisLayer
      REMOVE FriendlyCompDesc
      REMOVE LAYER_NETWORK_TYPE
      REMOVE ASSET_TYPE_LEVELS
      REMOVE RegisterSelectionType2
      REMOVE RegisterSelectionType3
      REMOVE RegisterUserfield1
      REMOVE RegisterUserfield2
      REMOVE Details
      REMOVE Description
      REMOVE ShortDescription
      REMOVE AcquisitionDate
      REMOVE OperatingStatus
      REMOVE PrimaryDimension
      REMOVE TemplateAssetNumber
      REMOVE PrimaryDimensionUnitOfMeasure
      REMOVE AssetAttributeSelectionType1-Level3
      REMOVE AssetAttributeSelectionType2-Level3
      REMOVE AssetAttributeSelectionType3-Level3
      REMOVE AssetAttributeSelectionType4-Level3
      REMOVE AssetAttributeSelectionType5-Level3
      REMOVE AssetAttributeSelectionType7-Level3
      REMOVE AssetAttributeSelectionType9-Level3
      REMOVE AssetAttributeUserfield1-Level3
      REMOVE AssetAttributeUserfield2-Level3
      REMOVE AssetAttributeUserfield3-Level3
      REMOVE AssetAttributeUserfield4-Level3
      REMOVE AssetAttributeUserfield5-Level3
      REMOVE AssetAttributeUserfield9-Level3
      REMOVE AssetAttributeUserfield10-Level3
      REMOVE AssetAttributeUserfield12-Level3
      REMOVE AssetAttributeUserfield13-Level3
      REMOVE AssetAttributeUserfield14-Level3
      REMOVE AssetAttributeSelectionType1-Level4
      REMOVE AssetAttributeSelectionType2-Level4
      REMOVE AssetAttributeSelectionType3-Level4
      REMOVE AssetAttributeSelectionType7-Level4
      REMOVE AssetAttributeSelectionType11-Level4
      REMOVE AssetAttributeUserfield3-Level4
      REMOVE AssetAttributeUserfield5-Level4
      REMOVE AssetAttributeUserfield9-Level4
      REMOVE AssetAttributeUserfield11-Level4
      REMOVE AssetAttributeUserfield13-Level4
      REMOVE AssetAttributeUserfield15-Level4
      REMOVE Asset
      REMOVE GIS_ID
      REMOVE fme_dataset
      REMOVE ASSETTYPE
      REMOVE DESCR
      REMOVE CRITICALITY
      REMOVE ALLOCATE
      REMOVE OLDGUID
      REMOVE created_user
      REMOVE created_date
      REMOVE last_edited_user
      REMOVE last_edited_date
      REMOVE SHAPE.STArea()
      REMOVE SHAPE.STLength()
      REMOVE SUBTYPE
      REMOVE BARLSHAPE
      REMOVE BARLDIM2
      REMOVE CHAMATL
      REMOVE TPWIDTH
      REMOVE BSWIDTH
      REMOVE CHDEPTH
      REMOVE UPNODE
      REMOVE DWNNODE
      REMOVE PIPEMATL
      REMOVE NOMDIAM
      REMOVE INTDIAM
      REMOVE OUTDIAM
      REMOVE INSTMTHD
      REMOVE LINEMATL
      REMOVE LINEMTHD
      REMOVE LINEDATE
      REMOVE COMPKEYREF
      REMOVE DEVCAREA
      REMOVE DVCMATL
    -> FinalFieldNames
AssetAttributesLevel3: AttributeManager
    ATTR_TABLE:
      REMOVE OBJECTID
      SET_TO LineType = ATTRIBUTE
      SET_TO AttributeCode = ASSET_TYPE
      SET_TO LevelNumber = 3
      REMOVE AssetNumber
      REMOVE ZCOORD
      REMOVE INSTDATE
      REMOVE UNITTYPE
      REMOVE ADDDBY
      REMOVE ADDDTTM
      REMOVE MODBY
      REMOVE MODDTTM
      REMOVE CONFIDENCE
      REMOVE OtherNumber
      REMOVE DATA_SRC
      REMOVE COMMENTS
      REMOVE GlobalID
      REMOVE SerialNumber
      REMOVE VALVESZ
      REMOVE ModelNumber
      REMOVE VALVESTAT
      REMOVE ManufacturerName
      REMOVE INVERTELEV
      REMOVE PIPELEN
      REMOVE SRVTYPE
      REMOVE CLASS
      REMOVE UPSELEV
      REMOVE DWNELEV
      REMOVE LENGTH
      REMOVE CONMATL
      REMOVE CHANSHAPE
      REMOVE fme_feature_type
      REMOVE JTTYPE
      REMOVE DPTH
      REMOVE METERSZ
      REMOVE CVRDIAM
      REMOVE BARLDIAM
      REMOVE CVRTYPE
      REMOVE GisLayer
      REMOVE FriendlyCompDesc
      REMOVE LAYER_NETWORK_TYPE
      REMOVE ASSET_TYPE_LEVELS
      REMOVE RegisterSelectionType2
      REMOVE RegisterSelectionType3
      REMOVE RegisterUserfield1
      REMOVE RegisterUserfield2
      REMOVE Details
      REMOVE Description
      REMOVE ShortDescription
      REMOVE AcquisitionDate
      REMOVE OperatingStatus
      REMOVE PrimaryDimension
      REMOVE TemplateAssetNumber
      REMOVE PrimaryDimensionUnitOfMeasure
      REMOVE AssetAttributeSelectionType1-Level2
      REMOVE AssetAttributeSelectionType1-Level4
      REMOVE AssetAttributeSelectionType2-Level4
      REMOVE AssetAttributeSelectionType3-Level4
      REMOVE AssetAttributeSelectionType7-Level4
      REMOVE AssetAttributeSelectionType11-Level4
      REMOVE AssetAttributeUserfield3-Level4
      REMOVE AssetAttributeUserfield5-Level4
      REMOVE AssetAttributeUserfield9-Level4
      REMOVE AssetAttributeUserfield11-Level4
      REMOVE AssetAttributeUserfield13-Level4
      REMOVE AssetAttributeUserfield15-Level4
      REMOVE Asset
      REMOVE GIS_ID
      REMOVE fme_dataset
      REMOVE ASSETTYPE
      REMOVE DESCR
      REMOVE CRITICALITY
      REMOVE ALLOCATE
      REMOVE OLDGUID
      REMOVE created_user
      REMOVE created_date
      REMOVE last_edited_user
      REMOVE last_edited_date
      REMOVE SHAPE.STArea()
      REMOVE SHAPE.STLength()
      REMOVE SUBTYPE
      REMOVE BARLSHAPE
      REMOVE BARLDIM2
      REMOVE CHAMATL
      REMOVE TPWIDTH
      REMOVE BSWIDTH
      REMOVE CHDEPTH
      REMOVE UPNODE
      REMOVE DWNNODE
      REMOVE PIPEMATL
      REMOVE NOMDIAM
      REMOVE INTDIAM
      REMOVE OUTDIAM
      REMOVE INSTMTHD
      REMOVE LINEMATL
      REMOVE LINEMTHD
      REMOVE LINEDATE
      REMOVE COMPKEYREF
      REMOVE DEVCAREA
      REMOVE DVCMATL
    -> FinalFieldNames
AssetAttributesLevel4: AttributeManager
    ATTR_TABLE:
      REMOVE OBJECTID
      SET_TO LineType = ATTRIBUTE
      SET_TO AttributeCode = ASSET_TYPE
      SET_TO LevelNumber = 4
      REMOVE AssetNumber
      REMOVE ZCOORD
      REMOVE INSTDATE
      REMOVE UNITTYPE
      REMOVE ADDDBY
      REMOVE ADDDTTM
      REMOVE MODBY
      REMOVE MODDTTM
      REMOVE CONFIDENCE
      REMOVE OtherNumber
      REMOVE DATA_SRC
      REMOVE COMMENTS
      REMOVE GlobalID
      REMOVE SerialNumber
      REMOVE VALVESZ
      REMOVE ModelNumber
      REMOVE VALVESTAT
      REMOVE ManufacturerName
      REMOVE INVERTELEV
      REMOVE PIPELEN
      REMOVE SRVTYPE
      REMOVE CLASS
      REMOVE UPSELEV
      REMOVE DWNELEV
      REMOVE LENGTH
      REMOVE CONMATL
      REMOVE CHANSHAPE
      REMOVE fme_feature_type
      REMOVE JTTYPE
      REMOVE DPTH
      REMOVE METERSZ
      REMOVE CVRDIAM
      REMOVE BARLDIAM
      REMOVE CVRTYPE
      REMOVE GisLayer
      REMOVE FriendlyCompDesc
      REMOVE LAYER_NETWORK_TYPE
      REMOVE ASSET_TYPE_LEVELS
      REMOVE RegisterSelectionType2
      REMOVE RegisterSelectionType3
      REMOVE RegisterUserfield1
      REMOVE RegisterUserfield2
      REMOVE Details
      REMOVE Description
      REMOVE ShortDescription
      REMOVE AcquisitionDate
      REMOVE OperatingStatus
      REMOVE PrimaryDimension
      REMOVE TemplateAssetNumber
      REMOVE PrimaryDimensionUnitOfMeasure
      REMOVE AssetAttributeSelectionType1-Level2
      REMOVE AssetAttributeSelectionType1-Level3
      REMOVE AssetAttributeSelectionType2-Level3
      REMOVE AssetAttributeSelectionType3-Level3
      REMOVE AssetAttributeSelectionType4-Level3
      REMOVE AssetAttributeSelectionType5-Level3
      REMOVE AssetAttributeSelectionType7-Level3
      REMOVE AssetAttributeSelectionType9-Level3
      REMOVE AssetAttributeUserfield1-Level3
      REMOVE AssetAttributeUserfield2-Level3
      REMOVE AssetAttributeUserfield3-Level3
      REMOVE AssetAttributeUserfield4-Level3
      REMOVE AssetAttributeUserfield5-Level3
      REMOVE AssetAttributeUserfield9-Level3
      REMOVE AssetAttributeUserfield10-Level3
      REMOVE AssetAttributeUserfield12-Level3
      REMOVE AssetAttributeUserfield13-Level3
      REMOVE AssetAttributeUserfield14-Level3
      REMOVE Asset
      REMOVE GIS_ID
      REMOVE fme_dataset
      REMOVE ASSETTYPE
      REMOVE DESCR
      REMOVE CRITICALITY
      REMOVE ALLOCATE
      REMOVE OLDGUID
      REMOVE created_user
      REMOVE created_date
      REMOVE last_edited_user
      REMOVE last_edited_date
      REMOVE SHAPE.STArea()
      REMOVE SHAPE.STLength()
      REMOVE SUBTYPE
      REMOVE BARLSHAPE
      REMOVE BARLDIM2
      REMOVE CHAMATL
      REMOVE TPWIDTH
      REMOVE BSWIDTH
      REMOVE CHDEPTH
      REMOVE UPNODE
      REMOVE DWNNODE
      REMOVE PIPEMATL
      REMOVE NOMDIAM
      REMOVE INTDIAM
      REMOVE OUTDIAM
      REMOVE INSTMTHD
      REMOVE LINEMATL
      REMOVE LINEMTHD
      REMOVE LINEDATE
      REMOVE COMPKEYREF
      REMOVE DEVCAREA
      REMOVE DVCMATL
    -> StormwaterOnly
StormwaterOnly: TestFilter
    DEFAULT_VALUE = <UNFILTERED>
    PASSED_TEST_GROUP_OUTPUT = FIRST
    TEST_LIST = "BOOL_OP,OR,COMPOSITE_TEST,""""""1"""""",TEST_CLAUSE,CASE_INSENSITIVE_TEST @Value(SearchPath) CONTAINS Network\Stormwater\",@Value(SearchPath) CONTAINS Network\Stormwater\
    @Value(SearchPath) CONTAINS Network\Stormwater\ -> FinalFieldNames
FinalFieldNames: AttributeManager
    ATTR_TABLE:
      RENAME_SET_VALUE AssetAttributeSelectionType1-Level2 > AssetAttributeSelectionType1
      RENAME_SET_VALUE AssetAttributeSelectionType1-Level3 > AssetAttributeSelectionType1
      RENAME_SET_VALUE AssetAttributeSelectionType2-Level3 > AssetAttributeSelectionType2
      RENAME_SET_VALUE AssetAttributeSelectionType3-Level3 > AssetAttributeSelectionType3
      RENAME_SET_VALUE AssetAttributeSelectionType4-Level3 > AssetAttributeSelectionType4
      RENAME_SET_VALUE AssetAttributeSelectionType5-Level3 > AssetAttributeSelectionType5
      RENAME_SET_VALUE AssetAttributeSelectionType7-Level3 > AssetAttributeSelectionType7
      RENAME_SET_VALUE AssetAttributeSelectionType9-Level3 > AssetAttributeSelectionType9
      RENAME_SET_VALUE AssetAttributeUserfield1-Level3 > AssetAttributeUserfield1
      RENAME_SET_VALUE AssetAttributeUserfield2-Level3 > AssetAttributeUserfield2
      RENAME_SET_VALUE AssetAttributeUserfield3-Level3 > AssetAttributeUserfield3
      RENAME_SET_VALUE AssetAttributeUserfield4-Level3 > AssetAttributeUserfield4
      RENAME_SET_VALUE AssetAttributeUserfield5-Level3 > AssetAttributeUserfield5
      RENAME_SET_VALUE AssetAttributeUserfield9-Level3 > AssetAttributeUserfield9
      RENAME_SET_VALUE AssetAttributeUserfield10-Level3 > AssetAttributeUserfield10
      RENAME_SET_VALUE AssetAttributeUserfield12-Level3 > AssetAttributeUserfield12
      RENAME_SET_VALUE AssetAttributeUserfield13-Level3 > AssetAttributeUserfield13
      RENAME_SET_VALUE AssetAttributeUserfield14-Level3 > AssetAttributeUserfield14
      RENAME_SET_VALUE AssetAttributeSelectionType1-Level4 > AssetAttributeSelectionType1
      RENAME_SET_VALUE AssetAttributeSelectionType2-Level4 > AssetAttributeSelectionType2
      RENAME_SET_VALUE AssetAttributeSelectionType3-Level4 > AssetAttributeSelectionType3
      RENAME_SET_VALUE AssetAttributeSelectionType7-Level4 > AssetAttributeSelectionType7
      RENAME_SET_VALUE AssetAttributeSelectionType11-Level4 > AssetAttributeSelectionType11
      RENAME_SET_VALUE AssetAttributeUserfield3-Level4 > AssetAttributeUserfield3
      RENAME_SET_VALUE AssetAttributeUserfield5-Level4 > AssetAttributeUserfield5
      RENAME_SET_VALUE AssetAttributeUserfield9-Level4 > AssetAttributeUserfield9
      RENAME_SET_VALUE AssetAttributeUserfield11-Level4 > AssetAttributeUserfield11
      RENAME_SET_VALUE AssetAttributeUserfield13-Level4 > AssetAttributeUserfield13
      RENAME_SET_VALUE AssetAttributeUserfield15-Level4 > AssetAttributeUserfield15
      REMOVE Asset
      REMOVE MERGENAME
      REMOVE NEWGlobalID
      REMOVE OLDGlobalID
    -> Sorter
Sorter
    SORT_PARM = GisId ALPHA ASCENDING AttributeCode ALPHA ASCENDING LevelNumber NUMERIC ASCENDING
    SORTED -> FinalTechOneFormat (writer CSV2_4)
FinalTechOneFormat (writer CSV2_4)
    attributes: LineType varchar(200), AssetRegisterName varchar(200), AssetNumber varchar(200), TemplateAssetNumber string, IgnoreAuditing varchar(200), Type varchar(200), Description varchar(200), Details varchar(200), ShortDescription varchar(200), Status varchar(200), OperatingStatus varchar(200), PrimaryDimension varchar(200), PrimaryDimensionUnitOfMeasure string, ManufacturerName varchar(20), SerialNumber varchar(20), ModelNumber varchar(20), OtherNumber string, AcquisitionDate varchar(200), FunctionSelectionCode varchar(200), CapacitySelectionCode varchar(200), UtilisationSelectionCode varchar(200), RiskConsequenceSelectionCode varchar(200), CriticalitySelectionCode string, RiskLikelihoodSelectionCode varchar(200), RegisterSelectionType2 varchar(254), RegisterSelectionType3 varchar(254), RegisterUserfield1 varchar(254), RegisterUserfield2 varchar(30), IsAvailableForDepreciationProcessing varchar(200), GisId varchar(200),
      GisLayer string, AttributeCode varchar(200), LevelNumber varchar(200), SearchPath string, AssetAttributeSelectionType4 varchar(200), AssetAttributeSelectionType5 varchar(200), AssetAttributeSelectionType9 varchar(200), AssetAttributeUserfield1 varchar(200), AssetAttributeUserfield2 varchar(200), AssetAttributeUserfield4 varchar(200), AssetAttributeUserfield10 varchar(200), AssetAttributeUserfield12 varchar(200), AssetAttributeSelectionType1 varchar(200), AssetAttributeUserfield14 varchar(200), AssetAttributeSelectionType2 varchar(200), AssetAttributeSelectionType3 varchar(200), AssetAttributeSelectionType7 varchar(200), AssetAttributeSelectionType11 varchar(200), AssetAttributeUserfield3 varchar(200), AssetAttributeUserfield5 varchar(200), AssetAttributeUserfield9 varchar(200), AssetAttributeUserfield11 varchar(200), AssetAttributeUserfield13 varchar(200), AssetAttributeUserfield15 varchar(200)

Bookmark: Merge Layer Details
Enterprise_LayerInfoLookup (reader CSV2_1)
    attributes: NewLayerName string, TemplateAssetNumber string, FriendlyCompDesc string, UNITTYPE string, PrimaryDimensionUnitOfMeasure string, LAYER_NETWORK_TYPE string, ASSET_TYPE_LEVELS string, SearchPath string
    -> AttributeManager_2
AttributeManager_2
    ATTR_TABLE = SET_TO MERGENAME = SDE.@Value(NewLayerName)
    -> MergeLayerAttributes [SUPPLIER]
MergeLayerAttributes: FeatureMerger
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = @Value(MERGENAME) @Value(MERGENAME) AUTO
    MERGE_TYPE = Attributes Only
    PROCESS_DUPS = YES
    REJECT_NULL_MISSING_KEYS = No
    SUPPLIERS_FIRST = No
    MERGED -> AssetNumberAdder [REQUESTOR]
