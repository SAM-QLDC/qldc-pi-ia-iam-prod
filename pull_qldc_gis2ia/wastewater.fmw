FME workspace wastewater.fmw

Readers:
- GEODATABASE_SDE_1: GEODATABASE_SDE

Bookmark: transform: polygons
wwPumpStation (reader GEODATABASE_SDE_1)
    attributes: OBJECTID integer, COMPKEY integer, ASSETTYPE char(10), DESCR char(254), SERVSTAT char(10), OWN char(10), ZCOORD double, INSTDATE date, ASBUILT char(30), SCHEME char(50), DATA_SRC char(20), COMMENTS char(254), ADDDBY char(20), ADDDTTM date, MODBY char(20), MODDTTM date, CONFIDENCE char(20), CRITICALITY integer, ALLOCATE range_domain(ALLOCATE_4:integer:0:100), OLDGUID char(40), created_user char(255), created_date date, last_edited_user char(255), last_edited_date date, GlobalID globalid, SHAPE.STArea() double, SHAPE.STLength() double
    -> Deaggregator
Deaggregator
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> _polygons [GeometryExtractor_Input_1]
_polygons: _polygons_2
    GeometryRemover_Output_2 -> AttributeManager_5
AttributeManager_5
    ATTR_TABLE = SET_TO id (varchar(200)) = FME_CONDITIONAL:DEFAULT_VALUE'@Value(COMPKEY)'BOOL_OP;OR;COMPOSITE_TEST;1;TEST _part_number ATTRIBUTE_HAS_A_VALUE _FME_BLANK_STRING_'@Value(COMPKEY)_@Value(_part_number)'FME_NUM_CONDITIONS2___
    -> Junction_3
Junction_3
    -> Junction_4
wwTreatmentPlant (reader GEODATABASE_SDE_1)
    attributes: OBJECTID integer, COMPKEY integer, ASSETTYPE char(10), DESCR char(254), SERVSTAT char(254), OWN char(254), ZCOORD double, INSTDATE date, ASBUILT char(20), SCHEME char(254), DATA_SRC char(20), COMMENTS char(254), ADDDBY char(20), ADDDTTM date, MODBY char(20), MODDTTM date, CONFIDENCE char(20), CRITICALITY double, ALLOCATE range_domain(ALLOCATE_4:integer:0:100), OLDGUID char(40), created_user char(255), created_date date, last_edited_user char(255), last_edited_date date, GlobalID globalid, SHAPE.STArea() double, SHAPE.STLength() double
    -> Deaggregator_2
Deaggregator_2
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> _polygons_2 [GeometryExtractor_Input_1]
_polygons_2
    GeometryRemover_Output_2 -> AttributeManager_6
AttributeManager_6
    ATTR_TABLE = SET_TO id (varchar(200)) = FME_CONDITIONAL:DEFAULT_VALUE'@Value(COMPKEY)'BOOL_OP;OR;COMPOSITE_TEST;1;TEST _part_number ATTRIBUTE_HAS_A_VALUE _FME_BLANK_STRING_'@Value(COMPKEY)_@Value(_part_number)'FME_NUM_CONDITIONS2___
    -> Junction_5
Junction_5
    -> Junction_6

Bookmark: load: 2csv
Junction_4
    -> polygons [Output]
Junction_6
    -> polygons [Output00]
polygons: FeatureWriter [off]
    CSV2_COORDINATE_SYSTEM_GRANULARITY = FEATURE_TYPE
    CSV2_DELIMITER = ,
    CSV2_ENCODING = UTF-8
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = if_needed
    CSV2_QUALIFY_FIELD_VALUES = if_needed
    CSV2_ROW_TERMINATION = System
    CSV2_TREAT_EMBEDDED_FIELD_QUALIFIERS_AS_UNSAFE = Yes
    CSV2_WRITE_BOM_FOR_UNICODE = Yes
    CSV2_WRITE_FIELD_NAMES = firstrow
    CSV2_WRITE_SCHEMA_FILE = NO
    DATASET = $(FME_MF_DIR_ENCODED)exports
    DATASET_ATTR = _dataset
    FEATURE_TYPE_LIST_ATTR = _feature_types
    FORMAT = CSV2
    TOTAL_FEATURES_WRITTEN_ATTR = _total_features_written
Junction_8
    -> linestring [Output00]
Junction_14
    -> nodes [Output]
Junction_10
    -> linestring [Output]
linestring: FeatureWriter [off]
    CSV2_COORDINATE_SYSTEM_GRANULARITY = FEATURE_TYPE
    CSV2_DELIMITER = ,
    CSV2_ENCODING = UTF-8
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = if_needed
    CSV2_QUALIFY_FIELD_VALUES = if_needed
    CSV2_ROW_TERMINATION = System
    CSV2_TREAT_EMBEDDED_FIELD_QUALIFIERS_AS_UNSAFE = Yes
    CSV2_WRITE_BOM_FOR_UNICODE = Yes
    CSV2_WRITE_FIELD_NAMES = firstrow
    CSV2_WRITE_SCHEMA_FILE = NO
    DATASET = $(FME_MF_DIR_ENCODED)exports
    DATASET_ATTR = _dataset
    FEATURE_TYPE_LIST_ATTR = _feature_types
    FORMAT = CSV2
    TOTAL_FEATURES_WRITTEN_ATTR = _total_features_written
Junction_2
    -> nodes [Output03]
nodes: FeatureWriter [off]
    CSV2_COORDINATE_SYSTEM_GRANULARITY = FEATURE_TYPE
    CSV2_DELIMITER = ,
    CSV2_ENCODING = UTF-8
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = if_needed
    CSV2_QUALIFY_FIELD_VALUES = if_needed
    CSV2_ROW_TERMINATION = System
    CSV2_TREAT_EMBEDDED_FIELD_QUALIFIERS_AS_UNSAFE = Yes
    CSV2_WRITE_BOM_FOR_UNICODE = Yes
    CSV2_WRITE_FIELD_NAMES = firstrow
    CSV2_WRITE_SCHEMA_FILE = NO
    DATASET = $(FME_MF_DIR_ENCODED)exports
    DATASET_ATTR = _dataset
    FEATURE_TYPE_LIST_ATTR = _feature_types
    FORMAT = CSV2
    TOTAL_FEATURES_WRITTEN_ATTR = _total_features_written

Bookmark: transform: nodes
wwManhole (reader GEODATABASE_SDE_1)
    attributes: OBJECTID integer, COMPKEY integer, ASSETTYPE char(254), SUBTYPE char(254), DESCR char(254), SERVSTAT char(254), OWN char(254), ZCOORD double, INVERTELEV double, BARLSHAPE char(254), BARLDIAM double, BARLDIM2 double, CHAMATL char(254), CVRDIAM double, CVRTYPE char(254), MANUFCT char(20), INSTDATE date, ASBUILT char(30), SCHEME char(254), DATA_SRC char(20), COMMENTS char(254), ADDDBY char(20), ADDDTTM date, MODBY char(20), MODDTTM date, CONFIDENCE char(10), CRITICALITY double, ALLOCATE range_domain(ALLOCATE_4:integer:0:100), OLDGUID char(40), GlobalID globalid,
      created_user char(255), created_date date, last_edited_user char(255), last_edited_date date
    -> _nodes [CoordinateExtractor_Input]
wwMeter (reader GEODATABASE_SDE_1)
    attributes: OBJECTID integer, COMPKEY integer, ASSETTYPE char(254), DESCR char(254), SERVSTAT char(254), OWN char(254), ZCOORD double, INVERTELEV double, METERSZ double, SERNO char(20), MODELNO char(20), MANUFCT char(20), INSTDATE date, ASBUILT char(30), SCHEME char(254), DATA_SRC char(20), COMMENTS char(254), ADDDBY char(20), ADDDTTM date, MODBY char(20), MODDTTM date, CONFIDENCE char(10), CRITICALITY double, ALLOCATE range_domain(ALLOCATE_4:integer:0:100), OLDGUID char(40), GlobalID globalid, created_user char(255), created_date date, last_edited_user char(255), last_edited_date date
    -> _nodes [CoordinateExtractor_Input]
wwValve (reader GEODATABASE_SDE_1)
    attributes: OBJECTID integer, COMPKEY integer, ASSETTYPE char(254), DESCR char(254), SERVSTAT char(254), OWN char(254), ZCOORD double, INVERTELEV double, VALVESTAT char(254), VALVESZ double, SERNO char(20), MODELNO char(20), MANUFCT char(20), INSTDATE date, ASBUILT char(30), SCHEME char(254), DATA_SRC char(20), COMMENTS char(254), ADDDBY char(20), ADDDTTM date, MODBY char(20), MODDTTM date, CONFIDENCE char(10), CRITICALITY double, ALLOCATE range_domain(ALLOCATE_4:integer:0:100), OLDGUID char(40), GlobalID globalid, created_user char(255), created_date date, last_edited_user char(255),
      last_edited_date date
    -> _nodes [CoordinateExtractor_Input]
wwNode (reader GEODATABASE_SDE_1)
    attributes: OBJECTID integer, COMPKEY integer, ASSETTYPE char(254), DESCR char(254), SERVSTAT char(254), OWN char(254), ZCOORD double, INVERTELEV double, INSTDATE date, ASBUILT char(30), SCHEME char(254), DATA_SRC char(20), COMMENTS char(254), ADDDBY char(20), ADDDTTM date, MODBY char(20), MODDTTM date, CONFIDENCE char(10), CRITICALITY double, ALLOCATE range_domain(ALLOCATE_4:integer:0:100), OLDGUID char(40), GlobalID globalid, created_user char(255), created_date date, last_edited_user char(255), last_edited_date date
    -> _nodes [CoordinateExtractor_Input]
_nodes
    GeometryRemover_Output -> AttributeManager
AttributeManager
    ATTR_TABLE:
      REMOVE _indices{}.x (real64)
      REMOVE _indices{}.y (real64)
      REMOVE _indices{}.z (real64)
    -> Junction
Junction
    -> Junction_2

Bookmark: transform: links
wwMain (reader GEODATABASE_SDE_1)
    attributes: OBJECTID integer, COMPKEY integer, ASSETTYPE char(254), DESCR char(254), SERVSTAT char(254), OWN char(254), PIPEMATL char(254), PIPELEN double, NOMDIAM double, INTDIAM double, OUTDIAM double, UPNODE char(20), UPSELEV double, DWNNODE char(20), DWNELEV double, CLASS char(254), INSTDATE date, JTTYPE char(254), MANUFCT char(20), INSTMTHD char(254), LINEMATL char(254), LINEMTHD char(254), LINEDATE date, ASBUILT char(30), SCHEME char(254), DATA_SRC char(20), COMMENTS char(254), ADDDBY char(20), ADDDTTM date, MODBY char(20),
      MODDTTM date, CONFIDENCE char(10), CRITICALITY double, ALLOCATE range_domain(ALLOCATE_4:integer:0:100), OLDGUID char(40), GlobalID globalid, created_user char(255), created_date date, last_edited_user char(255), last_edited_date date, SHAPE.STLength() double
    -> _linestring [ArcStroker_Input]
_linestring
    GeometryRemover_Output_1 -> AttributeManager_8
AttributeManager_8
    -> Junction_7
Junction_7
    -> Junction_8
wwLateral (reader GEODATABASE_SDE_1)
    attributes: OBJECTID integer, COMPKEY integer, ASSETTYPE char(254), SRVTYPE char(254), DESCR char(254), SERVSTAT char(254), OWN char(254), PIPEMATL char(254), PIPELEN double, NOMDIAM double, INTDIAM double, OUTDIAM double, CLASS char(254), MANUFCT char(20), INSTDATE date, ASBUILT char(30), SCHEME char(254), DATA_SRC char(20), COMMENTS char(254), ADDDBY char(20), ADDDTTM date, MODBY char(20), MODDTTM date, CONFIDENCE char(10), CRITICALITY double, ALLOCATE range_domain(ALLOCATE_4:integer:0:100), OLDGUID char(40), GlobalID globalid, created_user char(255), created_date date,
      last_edited_user char(255), last_edited_date date, SHAPE.STLength() double
    -> StartEnd [CoordinateExtractor_Input_1]
StartEnd
    AttributeCreator_Output -> _linestring_2 [ArcStroker_Input]
_linestring_2
    GeometryRemover_Output_1 -> AttributeManager_7
AttributeManager_7
    ATTR_TABLE:
      REMOVE _indices{}.x (real64)
      REMOVE _indices{}.y (real64)
      REMOVE _indices{}.z (real64)
      REMOVE _element_count (uint64)
    -> Junction_9
    -> Junction_11
Junction_11
    -> Junction_12
Junction_9
    -> Junction_10

Bookmark: transform: connection nodes
Junction_12
    -> VertexCreator
    -> VertexCreator_2
VertexCreator
    MEASURE_TYPE = Continuous
    MODE_NAME = Replace with Point
    XVAL = @Value(x_start)
    YVAL = @Value(y_start)
    -> AttributeKeeper
AttributeKeeper
    CREATE_BULK_MODE_FEATURES = NO
    KEEP_ATTRS = COMPKEY
    -> AttributeCreator
AttributeCreator
    ATTR_TABLE = SET_TO COMPKEY (int32) = @Value(COMPKEY)_US
    -> Junction_13
VertexCreator_2
    MEASURE_TYPE = Continuous
    MODE_NAME = Replace with Point
    XVAL = @Value(x_end)
    YVAL = @Value(y_end)
    -> AttributeKeeper_2
AttributeKeeper_2
    CREATE_BULK_MODE_FEATURES = NO
    KEEP_ATTRS = COMPKEY
    -> AttributeCreator_2
AttributeCreator_2
    ATTR_TABLE = SET_TO COMPKEY (int32) = @Value(COMPKEY)_DS
    -> Junction_13
Junction_13
    -> Junction_14

FME custom transformer _linestring

ArcStroker_Input (input)
    -> ArcStroker
GeometryRemover_Output_1 (output)

Bookmark: New Bookmark
ArcStroker
    MAKE_POLY = No
    NUM = 0
    STROKE_CHOICE = Number of Interpolated Edges
    STROKED -> GeometryExtractor
GeometryExtractor
    ATTR = point_array
    KIND_LONG = OGC Well Known Text
    OGCVERSION = 1.2
    OGC_WKT_PRECISION_DISPLAY = 64-bit
    REMOVE_GEOMETRY = No
    -> StringReplacer
    <REJECTED> -> GeometryExtractor__Rejected_
StringReplacer
    CASE = NO
    FIND_TEXT = LINESTRING (
    NO_MATCH = _FME_NO_OP_
    REGEXP = NO
    REPLACE_TEXT = {
    SRC_ATTRS = point_array
    -> StringReplacer_2
StringReplacer_2
    CASE = NO
    FIND_TEXT = )
    NO_MATCH = _FME_NO_OP_
    REGEXP = NO
    REPLACE_TEXT = }
    SRC_ATTRS = point_array
    -> StringReplacer_3
StringReplacer_3
    CASE = NO
    FIND_TEXT = " "
    NO_MATCH = _FME_NO_OP_
    REGEXP = NO
    REPLACE_TEXT = ,
    SRC_ATTRS = point_array
    -> GeometryRemover
GeometryRemover
    REMOVE_COORDSYS = No
    -> GeometryRemover_Output_1 (output)
GeometryExtractor__Rejected_: Logger
    LOG_FEATURE = LOG_ONLY
    MAXCOORDS = 20
    MAXFEATS = 20
    MESSAGE = Feature is:
    SEVERITY = INFO

FME custom transformer StartEnd

CoordinateExtractor_Input_1 (input)
    -> CoordinateExtractor
AttributeCreator_Output (output)

Bookmark: New Bookmark
CoordinateExtractor
    LIST_NAME = _indices
    MODE = All Coordinates
    -> ListElementCounter
ListElementCounter
    CNT_ATTR = _element_count
    LIST_NAME = _indices{}
    -> AttributeCreator
AttributeCreator
    ATTR_TABLE:
      SET_TO x_start (varchar(200)) = @Double(@Value(_indices{0}.x))
      SET_TO y_start (varchar(200)) = @Double(@Value(_indices{0}.y))
      SET_TO x_end (varchar(200)) = @Double(@Value(_indices{@Evaluate(@Value(_element_count)-1)}.x))
      SET_TO y_end (varchar(200)) = @Double(@Value(_indices{@Evaluate(@Value(_element_count)-1)}.y))
    -> AttributeCreator_Output (output)

FME custom transformer _polygons_2

GeometryExtractor_Input_1 (input)
    -> GeometryExtractor
GeometryRemover_Output_2 (output)

Bookmark: New Bookmark
GeometryExtractor
    ATTR = point_array
    KIND_LONG = OGC Well Known Text
    OGCVERSION = 1.2
    OGC_WKT_PRECISION_DISPLAY = 64-bit
    REMOVE_GEOMETRY = No
    -> StringReplacer
StringReplacer
    CASE = NO
    FIND_TEXT = POLYGON (
    NO_MATCH = _FME_NO_OP_
    REGEXP = NO
    SRC_ATTRS = point_array
    -> StringReplacer_2
StringReplacer_2
    CASE = NO
    FIND_TEXT = (
    NO_MATCH = _FME_NO_OP_
    REGEXP = NO
    REPLACE_TEXT = {
    SRC_ATTRS = point_array
    -> StringReplacer_3
StringReplacer_3
    CASE = NO
    FIND_TEXT = ))
    NO_MATCH = _FME_NO_OP_
    REGEXP = NO
    REPLACE_TEXT = }
    SRC_ATTRS = point_array
    -> StringReplacer_4
StringReplacer_4
    CASE = NO
    FIND_TEXT = " "
    NO_MATCH = _FME_NO_OP_
    REGEXP = NO
    REPLACE_TEXT = ,
    SRC_ATTRS = point_array
    -> GeometryRemover
GeometryRemover
    REMOVE_COORDSYS = No
    -> GeometryRemover_Output_2 (output)

FME custom transformer _links

FME custom transformer _nodes

CoordinateExtractor_Input (input)
    -> CoordinateExtractor
GeometryRemover_Output (output)

Bookmark: New Bookmark
CoordinateExtractor
    LIST_NAME = _indices
    MODE = All Coordinates
    -> AttributeCreator
AttributeCreator
    ATTR_TABLE:
      SET_TO x (varchar(200)) = @Value(_indices{0}.x)
      SET_TO y (varchar(200)) = @Value(_indices{0}.y)
    -> GeometryRemover
GeometryRemover
    REMOVE_COORDSYS = No
    -> GeometryRemover_Output (output)
