FME workspace water supply.fmw

Readers:
- GEODATABASE_SDE_1: GEODATABASE_SDE

Bookmark: transform: wsNodes
wsBackflow (reader GEODATABASE_SDE_1)
    attributes: OBJECTID integer, COMPKEY integer, ASSETTYPE char(254), DESCR char(254), SERVSTAT char(254), OWN char(254), ZCOORD double, INVERTELEV double, VALVESTAT char(254), VALVESZ double, SERNO char(20), MODELNO char(20), MANUFCT char(20), INSTDATE date, ASBUILT char(30), SCHEME char(254), DATA_SRC char(20), COMMENTS char(254), ADDDBY char(20), ADDDTTM date, MODBY char(20), MODDTTM date, CONFIDENCE char(10), CRITICALITY double, ALLOCATE range_domain(ALLOCATE_4:integer:0:100), OLDGUID char(40), GlobalID globalid, created_user char(255), created_date date, last_edited_user char(255),
      last_edited_date date
    -> _nodes [CoordinateExtractor_Input]
wsValve (reader GEODATABASE_SDE_1)
    attributes: OBJECTID integer, COMPKEY integer, ASSETTYPE char(254), DESCR char(254), SERVSTAT char(254), OWN char(254), ZCOORD double, INVERTELEV double, VALVESTAT char(254), VALVESZ double, SERNO char(20), MODELNO char(20), MANUFCT char(20), INSTDATE date, ASBUILT char(30), SCHEME char(254), DATA_SRC char(20), COMMENTS char(254), ADDDBY char(20), ADDDTTM date, MODBY char(20), MODDTTM date, CONFIDENCE char(10), CRITICALITY double, ALLOCATE range_domain(ALLOCATE_4:integer:0:100), OLDGUID char(40), GlobalID globalid, created_user char(255), created_date date, last_edited_user char(255),
      last_edited_date date
    -> _nodes [CoordinateExtractor_Input]
_nodes
    GeometryRemover_Output -> AttributeCreator_2
AttributeCreator_2
    ATTR_TABLE = SET_TO feature (varchar(50)) = @Value(fme_feature_type)
    -> Junction
Junction
    -> Junction_2
    -> Junction_7
wsHydrant (reader GEODATABASE_SDE_1) [off]
    attributes: OBJECTID integer, COMPKEY integer, ASSETTYPE char(254), DESCR char(254), SERVSTAT char(254), OWN char(254), ZCOORD double, INVERTELEV double, MODELNO char(20), MANUFCT char(20), INSTDATE date, ASBUILT char(30), SCHEME char(254), DATA_SRC char(20), COMMENTS char(254), ADDDBY char(20), ADDDTTM date, MODBY char(20), MODDTTM date, CONFIDENCE char(10), CRITICALITY double, ALLOCATE range_domain(ALLOCATE_4:integer:0:100), OLDGUID char(40), GlobalID globalid, created_user char(255), created_date date, last_edited_user char(255), last_edited_date date
    -> _nodes_3 [CoordinateExtractor_Input]
_nodes_3
    GeometryRemover_Output -> Junction_13
Junction_13
    -> Junction_14
    -> Junction_7
wsMeter (reader GEODATABASE_SDE_1) [off]
    attributes: OBJECTID integer, COMPKEY integer, ASSETTYPE char(254), DESCR char(254), SERVSTAT char(254), OWN char(254), ZCOORD double, INVERTELEV double, METERSZ double, SERNO char(20), MODELNO char(20), MANUFCT char(20), INSTDATE date, ASBUILT char(30), SCHEME char(254), DATA_SRC char(20), COMMENTS char(254), ADDDBY char(20), ADDDTTM date, MODBY char(20), MODDTTM date, CONFIDENCE char(10), CRITICALITY double, ALLOCATE range_domain(ALLOCATE_4:integer:0:100), OLDGUID char(40), GlobalID globalid, created_user char(255), created_date date, last_edited_user char(255), last_edited_date date
    -> _nodes_4 [CoordinateExtractor_Input]
_nodes_4
    GeometryRemover_Output -> Junction_15
Junction_15
    -> Junction_16
    -> Junction_7
wsNode (reader GEODATABASE_SDE_1) [off]
    attributes: OBJECTID integer, COMPKEY integer, ASSETTYPE char(254), DESCR char(254), SERVSTAT char(254), OWN char(254), ZCOORD double, INVERTELEV double, INSTDATE date, ASBUILT char(30), SCHEME char(254), DATA_SRC char(20), COMMENTS char(254), ADDDBY char(20), ADDDTTM date, MODBY char(20), MODDTTM date, CONFIDENCE char(10), CRITICALITY double, ALLOCATE range_domain(ALLOCATE_4:integer:0:100), OLDGUID char(40), GlobalID globalid, created_user char(255), created_date date, last_edited_user char(255), last_edited_date date
    -> _nodes_5 [CoordinateExtractor_Input]
_nodes_5
    GeometryRemover_Output -> Junction_17
Junction_17
    -> Junction_18
    -> Junction_7
Junction_7
    -> Junction_8

Bookmark: load: nodes 2csv
Junction_2
    -> DateTimeConverter_2
DateTimeConverter_2
    DATETIME_ATTR = ADDDTTM INSTDATE created_date MODDTTM last_edited_date
    OUT_FORMAT = %Y%m%d%H%M%S
    PASSTHROUGH = NO
    REPAIR_INPUT = YES
    -> FeatureWriter [_Rejected_]
    <REJECTED> -> FeatureWriter [_Rejected_]
Junction_14
    -> DateTimeConverter_6
DateTimeConverter_6
    DATETIME_ATTR = ADDDTTM INSTDATE created_date MODDTTM last_edited_date
    OUT_FORMAT = %Y%m%d%H%M%S
    PASSTHROUGH = NO
    REPAIR_INPUT = YES
    -> FeatureWriter [_Rejected_00]
    <REJECTED> -> FeatureWriter [_Rejected_00]
Junction_16
    -> DateTimeConverter_7
DateTimeConverter_7
    DATETIME_ATTR = ADDDTTM INSTDATE created_date MODDTTM last_edited_date
    OUT_FORMAT = %Y%m%d%H%M%S
    PASSTHROUGH = NO
    REPAIR_INPUT = YES
    -> FeatureWriter [_Rejected_01]
    <REJECTED> -> FeatureWriter [_Rejected_01]
Junction_18
    -> DateTimeConverter_8
DateTimeConverter_8
    DATETIME_ATTR = ADDDTTM INSTDATE created_date MODDTTM last_edited_date
    OUT_FORMAT = %Y%m%d%H%M%S
    PASSTHROUGH = NO
    REPAIR_INPUT = YES
    -> FeatureWriter [_Rejected_02]
    <REJECTED> -> FeatureWriter [_Rejected_02]
FeatureWriter
    CSV2_COORDINATE_SYSTEM_GRANULARITY = FEATURE_TYPE
    CSV2_DELIMITER = ,
    CSV2_ENCODING = UTF-8
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = if_needed
    CSV2_QUALIFY_FIELD_VALUES = if_needed
    CSV2_ROW_TERMINATION = System
    CSV2_TREAT_EMBEDDED_FIELD_QUALIFIERS_AS_UNSAFE = Yes
    CSV2_WRITE_BOM_FOR_UNICODE = Yes
    CSV2_WRITE_FIELD_NAMES = firstrow
    CSV2_WRITE_SCHEMA_FILE = NO
    DATASET = $(FME_MF_DIR_ENCODED)exports
    DATASET_ATTR = _dataset
    FEATURE_TYPE_LIST_ATTR = _feature_types
    FORMAT = CSV2
    TOTAL_FEATURES_WRITTEN_ATTR = _total_features_written

Bookmark: edm: unique values wsNodes
Junction_8
    -> AttributeKeeper
    -> AttributeKeeper_2
    -> AttributeKeeper_3
AttributeKeeper
    CREATE_BULK_MODE_FEATURES = NO
    KEEP_ATTRS = ASSETTYPE,fme_feature_type
    -> ASSETTYPE
ASSETTYPE: UniqueValueLogger
    VAL = @Value(ASSETTYPE)
AttributeKeeper_2
    CREATE_BULK_MODE_FEATURES = NO
    KEEP_ATTRS = fme_feature_type,SERVSTAT
    -> SERVSTAT
SERVSTAT: UniqueValueLogger
    VAL = @Value(SERVSTAT)
AttributeKeeper_3
    CREATE_BULK_MODE_FEATURES = NO
    KEEP_ATTRS = fme_feature_type,OWN
    -> OWN
OWN: UniqueValueLogger
    VAL = @Value(OWN)

Bookmark: transform: lines
wsMain (reader GEODATABASE_SDE_1) [off]
    attributes: OBJECTID integer, COMPKEY integer, ASSETTYPE char(254), DESCR char(254), SERVSTAT char(254), OWN char(254), PIPEMATL char(254), PIPELEN double, NOMDIAM double, INTDIAM double, OUTDIAM double, DPTH double, UPNODE char(50), DWNNODE char(50), CLASS char(254), JTTYPE char(254), MANUFCT char(20), INSTMTHD char(254), LINEMATL char(254), LINEMTHD char(254), LINEDATE date, INSTDATE date, ASBUILT char(30), SCHEME char(254), DATA_SRC char(20), COMMENTS char(254), ADDDBY char(20), ADDDTTM date, MODBY char(20), MODDTTM date,
      CONFIDENCE char(10), CRITICALITY double, ALLOCATE range_domain(ALLOCATE_4:integer:0:100), OLDGUID char(40), GlobalID globalid, created_user char(255), created_date date, last_edited_user char(255), last_edited_date date, SHAPE.STLength() double
    -> _startend [CoordinateExtractor_Input_1]
wsLateral (reader GEODATABASE_SDE_1) [off]
    attributes: OBJECTID integer, COMPKEY integer, ASSETTYPE char(20), SRVTYPE char(254), DESCR char(254), SERVSTAT char(254), OWN char(254), PIPEMATL char(254), PIPELEN double, NOMDIAM double, INTDIAM double, OUTDIAM double, CLASS char(254), MANUFCT char(20), INSTDATE date, ASBUILT char(30), SCHEME char(254), DATA_SRC char(20), COMMENTS char(254), ADDDBY char(20), ADDDTTM date, MODBY char(20), MODDTTM date, CONFIDENCE char(10), CRITICALITY double, ALLOCATE range_domain(ALLOCATE_4:integer:0:100), OLDGUID char(40), GlobalID globalid, created_user char(255), created_date date,
      last_edited_user char(255), last_edited_date date, SHAPE.STLength() double
    -> _startend [CoordinateExtractor_Input_1]
_startend
    AttributeCreator_Output -> _linestring [ArcStroker_Input]
_linestring
    GeometryRemover_Output_1 -> Junction_3
    GeometryRemover_Output_1 -> Junction_9
Junction_3
    -> Junction_4
Junction_9
    -> Junction_10

Bookmark: load: pipes 2csv
Junction_4
    -> DateTimeConverter_3
DateTimeConverter_3
    DATETIME_ATTR = ADDDTTM INSTDATE created_date MODDTTM last_edited_date
    OUT_FORMAT = %Y%m%d%H%M%S
    PASSTHROUGH = NO
    REPAIR_INPUT = YES
    -> FeatureWriter_2 [GeometryRemover_Output_1]
    <REJECTED> -> FeatureWriter_2 [GeometryRemover_Output_1]
FeatureWriter_2 [off]
    CSV2_COORDINATE_SYSTEM_GRANULARITY = FEATURE_TYPE
    CSV2_DELIMITER = ,
    CSV2_ENCODING = UTF-8
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = if_needed
    CSV2_QUALIFY_FIELD_VALUES = if_needed
    CSV2_ROW_TERMINATION = System
    CSV2_TREAT_EMBEDDED_FIELD_QUALIFIERS_AS_UNSAFE = Yes
    CSV2_WRITE_BOM_FOR_UNICODE = Yes
    CSV2_WRITE_FIELD_NAMES = firstrow
    CSV2_WRITE_SCHEMA_FILE = NO
    DATASET = $(FME_MF_DIR_ENCODED)exports
    DATASET_ATTR = _dataset
    FEATURE_TYPE_LIST_ATTR = _feature_types
    FORMAT = CSV2
    TOTAL_FEATURES_WRITTEN_ATTR = _total_features_written

Bookmark: edm: unique values wsLinks
Junction_10
    -> AttributeKeeper_4
    -> AttributeKeeper_5
    -> AttributeKeeper_6
AttributeKeeper_4
    CREATE_BULK_MODE_FEATURES = NO
    KEEP_ATTRS = ASSETTYPE,fme_feature_type
    -> ASSETTYPE_2
ASSETTYPE_2: UniqueValueLogger
    VAL = @Value(ASSETTYPE)
AttributeKeeper_5
    CREATE_BULK_MODE_FEATURES = NO
    KEEP_ATTRS = fme_feature_type,SERVSTAT
    -> SERVSTAT_2
SERVSTAT_2: UniqueValueLogger
    VAL = @Value(SERVSTAT)
AttributeKeeper_6
    CREATE_BULK_MODE_FEATURES = NO
    KEEP_ATTRS = fme_feature_type,OWN
    -> OWN_2
OWN_2: UniqueValueLogger
    VAL = @Value(OWN)

Bookmark: transform: polygons
wsPumpStation (reader GEODATABASE_SDE_1) [off]
    attributes: OBJECTID integer, COMPKEY integer, ASSETTYPE char(20), DESCR char(254), SERVSTAT char(254), OWN char(254), ZCOORD double, INSTDATE date, ASBUILT char(30), SCHEME char(254), DATA_SRC char(20), COMMENTS char(254), ADDDBY char(20), ADDDTTM date, MODBY char(20), MODDTTM date, CONFIDENCE char(10), CRITICALITY double, ALLOCATE range_domain(ALLOCATE_4:integer:0:100), OLDGUID char(40), created_user char(255), created_date date, last_edited_user char(255), last_edited_date date, GlobalID globalid, SHAPE.STArea() double, SHAPE.STLength() double
    -> Deaggregator
Deaggregator
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> _polygons [GeometryExtractor_Input_1]
_polygons: _polygons_2
    GeometryRemover_Output_2 -> Junction_5
wsReservoir (reader GEODATABASE_SDE_1) [off]
    attributes: OBJECTID integer, COMPKEY integer, ASSETTYPE char(10), DESCR char(254), SERVSTAT char(254), OWN char(254), ZCOORD double, INSTDATE date, ASBUILT char(30), SCHEME char(254), DATA_SRC char(20), COMMENTS char(254), ADDDBY char(20), ADDDTTM date, MODBY char(20), MODDTTM date, CONFIDENCE char(10), CRITICALITY double, ALLOCATE range_domain(ALLOCATE_4:integer:0:100), OLDGUID char(40), created_user char(255), created_date date, last_edited_user char(255), last_edited_date date, GlobalID globalid, SHAPE.STArea() double, SHAPE.STLength() double
    -> Deaggregator_2
Deaggregator_2
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> _polygons_2 [GeometryExtractor_Input_1]
_polygons_2
    GeometryRemover_Output_2 -> Junction_5
wsTreatmentPlant (reader GEODATABASE_SDE_1) [off]
    attributes: OBJECTID integer, COMPKEY integer, ASSETTYPE char(10), DESCR char(254), SERVSTAT char(254), OWN char(254), ZCOORD double, INSTDATE date, ASBUILT char(30), SCHEME char(254), DATA_SRC char(20), COMMENTS char(254), ADDDBY char(20), ADDDTTM date, MODBY char(20), MODDTTM date, CONFIDENCE char(10), CRITICALITY double, ALLOCATE range_domain(ALLOCATE_4:integer:0:100), OLDGUID char(40), created_user char(255), created_date date, last_edited_user char(255), last_edited_date date, GlobalID globalid, SHAPE.STArea() double, SHAPE.STLength() double
    -> Deaggregator_3
Deaggregator_3
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> _polygons_3 [GeometryExtractor_Input_1]
_polygons_3: _polygons_2
    GeometryRemover_Output_2 -> Junction_5
Junction_5
    -> Junction_6
wsMiscellaneous (reader GEODATABASE_SDE_1) [off]
    attributes: OBJECTID integer, COMPKEY integer, ASSETTYPE char(254), DESCR char(254), SERVSTAT char(254), OWN char(254), ZCOORD double, INSTDATE date, ASBUILT char(30), SCHEME char(254), DATA_SRC char(20), COMMENTS char(254), ADDDBY char(20), ADDDTTM date, MODBY char(20), MODDTTM date, CONFIDENCE char(10), CRITICALITY double, ALLOCATE range_domain(ALLOCATE_4:integer:0:100), OLDGUID char(40), GlobalID globalid, created_user char(255), created_date date, last_edited_user char(255), last_edited_date date, SHAPE.STArea() double, SHAPE.STLength() double
    -> GeometryExtractor
GeometryExtractor
    ATTR = _geometry
    KIND_LONG = OGC Well Known Text
    OGCVERSION = 1.2
    OGC_WKT_PRECISION_DISPLAY = 64-bit
    REMOVE_GEOMETRY = No
    -> TestFilter
TestFilter
    DEFAULT_VALUE = <UNFILTERED>
    PASSED_TEST_GROUP_OUTPUT = FIRST
    TEST_LIST = "BOOL_OP,OR,COMPOSITE_TEST,""""""1"""""",TEST_CLAUSE,CASE_INSENSITIVE_TEST @Value(_geometry) BEGINS_WITH POINT",point,"BOOL_OP,OR,COMPOSITE_TEST,""""""1"""""",TEST_CLAUSE,CASE_INSENSITIVE_TEST @Value(_geometry) BEGINS_WITH LINE",line,"BOOL_OP,OR,COMPOSITE_TEST,""""""1"""""",TEST_CLAUSE,CASE_INSENSITIVE_TEST @Value(_geometry) BEGINS_WITH POLY",polygon,"BOOL_OP,OR,COMPOSITE_TEST,""""""1"""""",TEST_CLAUSE,CASE_INSENSITIVE_TEST @Value(_geometry) BEGINS_WITH MULTIPOLY",multi_polygon

Bookmark: load: polygons 2csv
Junction_6
    -> DateTimeConverter_4
DateTimeConverter_4
    DATETIME_ATTR = ADDDTTM INSTDATE created_date MODDTTM last_edited_date
    OUT_FORMAT = %Y%m%d%H%M%S
    PASSTHROUGH = NO
    REPAIR_INPUT = YES
    -> AttributeCreator
    <REJECTED> -> AttributeCreator
AttributeCreator
    ATTR_TABLE = SET_TO id (varchar(200)) = FME_CONDITIONAL:DEFAULT_VALUE'@Value(COMPKEY)'BOOL_OP;OR;COMPOSITE_TEST;1;TEST _part_number ATTRIBUTE_HAS_A_VALUE _FME_BLANK_STRING_'@Value(COMPKEY)_@Value(_part_number)'FME_NUM_CONDITIONS2___
    -> TestFilter_2
TestFilter_2
    DEFAULT_VALUE = <UNFILTERED>
    PASSED_TEST_GROUP_OUTPUT = FIRST
    TEST_LIST = "BOOL_OP,OR,COMPOSITE_TEST,""""""1"""""",TEST_CLAUSE,TEST @Value(fme_feature_type) = SDE.wsPumpStation",wsPumpStation,"BOOL_OP,OR,COMPOSITE_TEST,""""""1"""""",TEST_CLAUSE,TEST @Value(fme_feature_type) = SDE.wsReservoir",wsReservoir,"BOOL_OP,OR,COMPOSITE_TEST,""""""1"""""",TEST_CLAUSE,TEST @Value(fme_feature_type) = SDE.wsTreatmentPlant",wsTreatmentPlant
    wsPumpStation -> FeatureWriter_3 [GeometryRemover_Output_2]
    wsReservoir -> FeatureWriter_3 [GeometryRemover_Output_200]
    wsTreatmentPlant -> FeatureWriter_3 [GeometryRemover_Output_201]
FeatureWriter_3 [off]
    CSV2_COORDINATE_SYSTEM_GRANULARITY = FEATURE_TYPE
    CSV2_DELIMITER = ,
    CSV2_ENCODING = UTF-8
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = if_needed
    CSV2_QUALIFY_FIELD_VALUES = if_needed
    CSV2_ROW_TERMINATION = System
    CSV2_TREAT_EMBEDDED_FIELD_QUALIFIERS_AS_UNSAFE = Yes
    CSV2_WRITE_BOM_FOR_UNICODE = Yes
    CSV2_WRITE_FIELD_NAMES = firstrow
    CSV2_WRITE_SCHEMA_FILE = NO
    DATASET = $(FME_MF_DIR_ENCODED)exports
    DATASET_ATTR = _dataset
    FEATURE_TYPE_LIST_ATTR = _feature_types
    FORMAT = CSV2
    TOTAL_FEATURES_WRITTEN_ATTR = _total_features_written

FME custom transformer _startend

CoordinateExtractor_Input_1 (input)
    -> CoordinateExtractor
CoordinateExtractor
    LIST_NAME = _indices
    MODE = All Coordinates
    -> ListElementCounter
    <REJECTED> -> CoordinateExtractor__Rejected_
CoordinateExtractor__Rejected_: Logger
    LOG_FEATURE = LOG_ONLY
    MAXCOORDS = 20
    MAXFEATS = 20
    MESSAGE = Feature is:
    SEVERITY = INFO
ListElementCounter
    CNT_ATTR = _element_count
    LIST_NAME = _indices{}
    -> AttributeCreator
AttributeCreator
    ATTR_TABLE:
      SET_TO x_start (real64) = @Value(_indices{0}.x)
      SET_TO y_start (real64) = @Value(_indices{0}.y)
      SET_TO x_end (real64) = @Value(_indices{@Evaluate(@Value(_element_count)-1)}.x)
      SET_TO y_end (real64) = @Value(_indices{@Evaluate(@Value(_element_count)-1)}.y)
    -> AttributeCreator_Output (output)
AttributeCreator_Output (output)

FME custom transformer UniqueValueLogger
Description
This transformer lists all of the unique values for a chosen attribute alongside  a count attribute of the number of occurrences of each of these values. The information is logged in both the Translation Window / Workspace log file, and stored in attributes.
This transformer is useful when you are creating a workspace and need to know the possible values to use in a filter.
Input Ports
Input: This transformer accepts any features with an attribute.
Output Ports
Output: Features are output with the attribute selected as the unique value to filter, and a new attribute containing the number of occurrences of each unique value. All other attributes are removed. 
_count: Number of occurrences of each unique value.
_value: Unique values of selected attribute.
Parameters
Attribute to Analyze: Select the attribute for the transformer to run analysis on. 
Notes
Transformer alternatives:
Duplicate Filter - Consider using this transformer if you are looking to get a list of unique values and do not need a _count attribute 
StatisticsCalculator - Setting the Group By mode to the attribute to analyze will produce the same result as this transformer, it may beuse If you would like to gather other statistics as well as count of the unique attributes.

Parameters:
- VAL =   # Attribute to Analyze

Input (input)
    -> AttributeCreator

Bookmark: Count unique attribute values
AttributeCreator
    ATTR_TABLE = SET_TO _value = $(VAL)
    -> AttributeKeeper
Note: Remove unwanted / attributes
AttributeKeeper
    CREATE_BULK_MODE_FEATURES = No
    KEEP_ATTRS = _value
    -> Aggregator
Note: Create aggregates of / features, grouped by / the target attribute value
Aggregator
    ACCUM_ATTRS_NAME = Merge Incoming Attributes
    AGGREGATE_TYPE = Homogeneous Collection (If Possible)
    COUNT_ATTR = _count
    GROUP_BY = _value
    MODE = Geometry - Assemble One Level
    SEP = ,
    AGGREGATE -> StringConcatenator
Note: Concatenate unique values / with their occurrence counts
StringConcatenator
    ACTION = Create New Attribute
    PARM_LINE = fme_basicstring:14%1%14%1:@Value(_value),@Value(_count)
    VAL_ATTR = _concatenated
    -> Sorter
Note: Sort output based on / occurrence count and / attribute value
Sorter
    SORT_PARM = _count NUMERIC DESCENDING _value ALPHA ASCENDING
    SORTED -> ListBuilder
    SORTED -> AttributeManager

Bookmark: Create output
AttributeManager
    ATTR_TABLE = REMOVE _concatenated
    -> Output (output)
Output (output)

Bookmark: Log unique attribute values
Note: Turn all input features / Into a single list
ListBuilder
    LIST_NAME = _list
    -> ListConcatenator
Note: Concatenate values of / the list into an attribute
ListConcatenator
    DROP_EMPTY_PARTS = No
    LIST_ATTR = _list{}._concatenated
    VAL_ATTR = UNIQUE VALUES
    -> StringConcatenator_2
Note: Add header
StringConcatenator_2
    ACTION = Create New Attribute
    PARM_LINE = "\n\nVALUE, COUNT\n@Value(UNIQUE VALUES)\n"
    VAL_ATTR = UNIQUE VALUES
    -> AttributeRemover_2
Note: Remote the list
AttributeRemover_2
    LIST_ATTRS = _list{}
    -> Logger
Note: Log the single feature / that contains the / output attribute
Logger
    LOG_FEATURE = LOG_RECORD
    MAXCOORDS = 1
    MAXFEATS = 1
    MESSAGE = Unique values:
    SEVERITY = INFO

FME custom transformer _nodes

CoordinateExtractor_Input (input)
    -> CoordinateExtractor
CoordinateExtractor
    LIST_NAME = _indices
    MODE = All Coordinates
    -> AttributeCreator
AttributeCreator
    ATTR_TABLE:
      SET_TO x (varchar(200)) = @Value(_indices{0}.x)
      SET_TO y (varchar(200)) = @Value(_indices{0}.y)
    -> GeometryRemover
GeometryRemover
    REMOVE_COORDSYS = No
    -> GeometryRemover_Output (output)
GeometryRemover_Output (output)

FME custom transformer _linestring

ArcStroker_Input (input)
    -> ArcStroker
GeometryRemover_Output_1 (output)

Bookmark: New Bookmark
ArcStroker
    MAKE_POLY = No
    NUM = 0
    STROKE_CHOICE = Number of Interpolated Edges
    STROKED -> GeometryExtractor
GeometryExtractor
    ATTR = point_array
    KIND_LONG = OGC Well Known Text
    OGCVERSION = 1.2
    OGC_WKT_PRECISION_DISPLAY = 64-bit
    REMOVE_GEOMETRY = No
    -> StringReplacer
    <REJECTED> -> GeometryExtractor__Rejected_
StringReplacer
    CASE = NO
    FIND_TEXT = LINESTRING (
    NO_MATCH = _FME_NO_OP_
    REGEXP = NO
    REPLACE_TEXT = {
    SRC_ATTRS = point_array
    -> StringReplacer_2
StringReplacer_2
    CASE = NO
    FIND_TEXT = )
    NO_MATCH = _FME_NO_OP_
    REGEXP = NO
    REPLACE_TEXT = }
    SRC_ATTRS = point_array
    -> StringReplacer_3
StringReplacer_3
    CASE = NO
    FIND_TEXT = " "
    NO_MATCH = _FME_NO_OP_
    REGEXP = NO
    REPLACE_TEXT = ,
    SRC_ATTRS = point_array
    -> GeometryRemover
GeometryRemover
    REMOVE_COORDSYS = No
    -> GeometryRemover_Output_1 (output)
GeometryExtractor__Rejected_: Logger
    LOG_FEATURE = LOG_ONLY
    MAXCOORDS = 20
    MAXFEATS = 20
    MESSAGE = Feature is:
    SEVERITY = INFO

FME custom transformer _polygons_2

GeometryExtractor_Input_1 (input)
    -> GeometryExtractor
GeometryRemover_Output_2 (output)

Bookmark: New Bookmark
GeometryExtractor
    ATTR = point_array
    KIND_LONG = OGC Well Known Text
    OGCVERSION = 1.2
    OGC_WKT_PRECISION_DISPLAY = 64-bit
    REMOVE_GEOMETRY = No
    -> StringReplacer
StringReplacer
    CASE = NO
    FIND_TEXT = POLYGON (
    NO_MATCH = _FME_NO_OP_
    REGEXP = NO
    SRC_ATTRS = point_array
    -> StringReplacer_2
StringReplacer_2
    CASE = NO
    FIND_TEXT = (
    NO_MATCH = _FME_NO_OP_
    REGEXP = NO
    REPLACE_TEXT = {
    SRC_ATTRS = point_array
    -> StringReplacer_3
StringReplacer_3
    CASE = NO
    FIND_TEXT = ))
    NO_MATCH = _FME_NO_OP_
    REGEXP = NO
    REPLACE_TEXT = }
    SRC_ATTRS = point_array
    -> StringReplacer_4
StringReplacer_4
    CASE = NO
    FIND_TEXT = " "
    NO_MATCH = _FME_NO_OP_
    REGEXP = NO
    REPLACE_TEXT = ,
    SRC_ATTRS = point_array
    -> GeometryRemover
GeometryRemover
    REMOVE_COORDSYS = No
    -> GeometryRemover_Output_2 (output)
