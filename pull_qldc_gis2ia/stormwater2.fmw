FME workspace stormwater2.fmw

Readers:
- GEODATABASE_SDE_1: GEODATABASE_SDE

Bookmark: transform: nodes
swTreatmentDevice (reader GEODATABASE_SDE_1)
    attributes: OBJECTID integer, COMPKEY char(200), ASSETTYPE char(254), DESCR char(254), SERVSTAT char(254), OWN char(254), ZCOORD double, INVERTELEV double, DEVCAREA double, BARLDIAM double, BARLDIM2 double, DVCMATL char(254), CVRDIAM double, CVRTYPE char(254), MANUFCT char(20), INSTDATE char(20), ASBUILT char(30), SCHEME char(254), DATA_SRC char(50), COMMENTS char(254), ADDDBY char(20), ADDDTTM date, MODBY char(20), MODDTTM date, CONFIDENCE char(20), CRITICALITY double, ALLOCATE range_domain(ALLOCATE_5:integer:0:100), OLDGUID char(40), GlobalID globalid, created_user char(255),
      created_date date, last_edited_user char(255), last_edited_date date
    -> _nodes_7 [CoordinateExtractor_Input]
_nodes_7
    GeometryRemover_Output -> AttributeManager_12
AttributeManager_12
    ATTR_TABLE:
      REMOVE _indices{}.x (real64)
      REMOVE _indices{}.y (real64)
      REMOVE _indices{}.z (real64)
    -> nodes [Output05]
swManhole (reader GEODATABASE_SDE_1)
    attributes: OBJECTID integer, COMPKEY integer, ASSETTYPE char(254), DESCR char(254), SERVSTAT char(254), OWN char(254), ZCOORD double, INVERTELEV double, BARLSHAPE char(254), BARLDIAM double, BARLDIM2 double, CHAMATL char(254), CVRDIAM double, CVRTYPE char(254), MANUFCT char(20), INSTDATE date, ASBUILT char(30), SCHEME char(254), DATA_SRC char(20), COMMENTS char(254), ADDDBY char(20), ADDDTTM date, MODBY char(20), MODDTTM date, CONFIDENCE char(10), CRITICALITY double, ALLOCATE range_domain(ALLOCATE_5:integer:0:100), OLDGUID char(40), GlobalID globalid, created_user char(255),
      created_date date, last_edited_user char(255), last_edited_date date
    -> _nodes [CoordinateExtractor_Input]
_nodes
    GeometryRemover_Output -> AttributeManager
AttributeManager
    ATTR_TABLE:
      REMOVE _indices{}.x (real64)
      REMOVE _indices{}.y (real64)
      REMOVE _indices{}.z (real64)
    -> nodes [Output]
swNode (reader GEODATABASE_SDE_1)
    attributes: OBJECTID integer, COMPKEY integer, ASSETTYPE char(254), DESCR char(254), SERVSTAT char(254), OWN char(254), ZCOORD double, INVERTELEV double, INSTDATE date, ASBUILT char(30), SCHEME char(254), DATA_SRC char(20), COMMENTS char(254), ADDDBY char(20), ADDDTTM date, MODBY char(20), MODDTTM date, CONFIDENCE char(10), CRITICALITY double, ALLOCATE range_domain(ALLOCATE_5:integer:0:100), OLDGUID char(40), GlobalID globalid, created_user char(255), created_date date, last_edited_user char(255), last_edited_date date
    -> _nodes_2 [CoordinateExtractor_Input]
_nodes_2
    GeometryRemover_Output -> AttributeManager_2
AttributeManager_2
    ATTR_TABLE:
      REMOVE _indices{}.x (real64)
      REMOVE _indices{}.y (real64)
      REMOVE _indices{}.z (real64)
    -> nodes [Output00]
swMeter (reader GEODATABASE_SDE_1)
    attributes: OBJECTID integer, COMPKEY integer, ASSETTYPE char(20), DESCR char(254), SERVSTAT char(254), OWN char(254), ZCOORD double, INVERTELEV double, METERSZ double, SERNO char(20), MODELNO char(20), INSTDATE date, ASBUILT char(30), SCHEME char(50), DATA_SRC char(20), COMMENTS char(254), ADDDBY char(20), ADDDTTM date, MODBY char(20), MODDTTM date, CONFIDENCE char(10), CRITICALITY double, ALLOCATE range_domain(ALLOCATE_5:integer:0:100), GlobalID globalid, created_user char(255), created_date date, last_edited_user char(255), last_edited_date date
    -> _nodes_3 [CoordinateExtractor_Input]
_nodes_3
    GeometryRemover_Output -> AttributeManager_3
AttributeManager_3
    ATTR_TABLE:
      REMOVE _indices{}.x (real64)
      REMOVE _indices{}.y (real64)
      REMOVE _indices{}.z (real64)
    -> nodes [Output01]
swValve (reader GEODATABASE_SDE_1)
    attributes: OBJECTID integer, COMPKEY integer, ASSETTYPE char(10), DESCR char(254), SERVSTAT char(254), OWN char(254), ZCOORD double, INVERTELEV double, VALVESTAT char(254), VALVESZ double, SERNO char(20), MODELNO char(20), MANUFCT char(20), INSTDATE date, ASBUILT char(30), SCHEME char(254), DATA_SRC char(20), COMMENTS char(254), ADDDBY char(20), ADDDTTM date, MODBY char(20), MODDTTM date, CONFIDENCE char(10), CRITICALITY double, ALLOCATE range_domain(ALLOCATE_5:integer:0:100), OLDGUID char(40), GlobalID globalid, created_user char(255), created_date date, last_edited_user char(255),
      last_edited_date date
    -> _nodes_4 [CoordinateExtractor_Input]
_nodes_4
    GeometryRemover_Output -> AttributeManager_4
AttributeManager_4
    ATTR_TABLE:
      REMOVE _indices{}.x (real64)
      REMOVE _indices{}.y (real64)
      REMOVE _indices{}.z (real64)
    -> nodes [Output02]
swInlet (reader GEODATABASE_SDE_1)
    attributes: OBJECTID integer, COMPKEY integer, ASSETTYPE char(254), DESCR char(254), SERVSTAT char(254), OWN char(254), ZCOORD double, INVERTELEV double, MANUFCT char(20), INSTDATE date, ASBUILT char(30), SCHEME char(254), DATA_SRC char(20), COMMENTS char(254), ADDDBY char(20), ADDDTTM date, MODBY char(20), MODDTTM date, CONFIDENCE char(10), CRITICALITY double, ALLOCATE range_domain(ALLOCATE_5:integer:0:100), OLDGUID char(40), GlobalID globalid, created_user char(255), created_date date, last_edited_user char(255), last_edited_date date
    -> _nodes_5 [CoordinateExtractor_Input]
_nodes_5
    GeometryRemover_Output -> AttributeManager_10
AttributeManager_10
    ATTR_TABLE:
      REMOVE _indices{}.x (real64)
      REMOVE _indices{}.y (real64)
      REMOVE _indices{}.z (real64)
    -> nodes [Output03]
swStructure (reader GEODATABASE_SDE_1)
    attributes: OBJECTID integer, COMPKEY integer, ASSETTYPE char(254), DESCR char(254), SERVSTAT char(254), OWN char(254), ZCOORD double, MANUFCT char(20), INSTDATE date, ASBUILT char(30), SCHEME char(254), DATA_SRC char(20), COMMENTS char(254), ADDDBY char(20), ADDDTTM date, MODBY char(20), MODDTTM date, CONFIDENCE char(10), CRITICALITY double, ALLOCATE range_domain(ALLOCATE_5:integer:0:100), OLDGUID char(40), GlobalID globalid, created_user char(255), created_date date, last_edited_user char(255), last_edited_date date
    -> _nodes_6 [CoordinateExtractor_Input]
_nodes_6
    GeometryRemover_Output -> AttributeManager_11
AttributeManager_11
    ATTR_TABLE:
      REMOVE _indices{}.x (real64)
      REMOVE _indices{}.y (real64)
      REMOVE _indices{}.z (real64)
    -> nodes [Output04]
nodes: FeatureWriter
    CSV2_COORDINATE_SYSTEM_GRANULARITY = FEATURE_TYPE
    CSV2_DELIMITER = ,
    CSV2_ENCODING = UTF-8
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = if_needed
    CSV2_QUALIFY_FIELD_VALUES = if_needed
    CSV2_ROW_TERMINATION = System
    CSV2_TREAT_EMBEDDED_FIELD_QUALIFIERS_AS_UNSAFE = Yes
    CSV2_WRITE_BOM_FOR_UNICODE = Yes
    CSV2_WRITE_FIELD_NAMES = firstrow
    CSV2_WRITE_SCHEMA_FILE = NO
    DATASET = $(FME_MF_DIR_ENCODED)exports
    DATASET_ATTR = _dataset
    FEATURE_TYPE_LIST_ATTR = _feature_types
    FORMAT = CSV2
    TOTAL_FEATURES_WRITTEN_ATTR = _total_features_written

Bookmark: transform: polygons
swTreatmentDeviceArea (reader GEODATABASE_SDE_1)
    attributes: OBJECTID integer, COMPKEYREF integer, COMMENTS char(254), ADDDBY char(20), ADDDTTM date, MODBY char(20), MODDTTM date, GlobalID globalid, created_user char(255), created_date date, last_edited_user char(255), last_edited_date date, SHAPE.STArea() double, SHAPE.STLength() double
    -> _polygons_2 [GeometryExtractor_Input_1]
_polygons_2
    GeometryRemover_Output_2 -> AttributeManager_6
AttributeManager_6
    -> polygons [Output00]
swPumpstation (reader GEODATABASE_SDE_1)
    attributes: OBJECTID integer, COMPKEY integer, ASSETTYPE char(10), DESCR char(254), SERVSTAT char(254), OWN char(254), ZCOORD double, INSTDATE date, ASBUILT char(30), SCHEME char(254), DATA_SRC char(20), COMMENTS char(254), ADDDBY char(20), ADDDTTM date, MODBY char(20), MODDTTM date, CONFIDENCE char(20), CRITICALITY double, ALLOCATE range_domain(ALLOCATE_5:integer:0:100), GlobalID globalid, created_user char(255), created_date date, last_edited_user char(255), last_edited_date date, SHAPE.STArea() double, SHAPE.STLength() double
    -> _polygons [GeometryExtractor_Input_1]
_polygons: _polygons_2
    GeometryRemover_Output_2 -> AttributeManager_5
AttributeManager_5
    -> polygons [Output]
polygons: FeatureWriter
    CSV2_COORDINATE_SYSTEM_GRANULARITY = FEATURE_TYPE
    CSV2_DELIMITER = ,
    CSV2_ENCODING = UTF-8
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = if_needed
    CSV2_QUALIFY_FIELD_VALUES = if_needed
    CSV2_ROW_TERMINATION = System
    CSV2_TREAT_EMBEDDED_FIELD_QUALIFIERS_AS_UNSAFE = Yes
    CSV2_WRITE_BOM_FOR_UNICODE = Yes
    CSV2_WRITE_FIELD_NAMES = firstrow
    CSV2_WRITE_SCHEMA_FILE = NO
    DATASET = $(FME_MF_DIR_ENCODED)exports
    DATASET_ATTR = _dataset
    FEATURE_TYPE_LIST_ATTR = _feature_types
    FORMAT = CSV2
    TOTAL_FEATURES_WRITTEN_ATTR = _total_features_written

Bookmark: transform: lines
swMain (reader GEODATABASE_SDE_1)
    attributes: OBJECTID integer, COMPKEY integer, ASSETTYPE char(254), DESCR char(254), SERVSTAT char(254), OWN char(254), PIPEMATL char(254), PIPELEN double, NOMDIAM double, INTDIAM double, OUTDIAM double, UPNODE char(20), UPSELEV double, DWNNODE char(20), DWNELEV double, CLASS char(254), JTTYPE char(254), MANUFCT char(20), INSTMTHD char(254), INSTDATE date, LINEMATL char(254), LINEMTHD char(254), LINEDATE date, ASBUILT char(30), SCHEME char(254), DATA_SRC char(20), COMMENTS char(254), ADDDBY char(20), ADDDTTM date, MODBY char(20),
      MODDTTM date, CONFIDENCE char(10), CRITICALITY double, ALLOCATE range_domain(ALLOCATE_5:integer:0:100), OLDGUID char(40), GlobalID globalid, created_user char(255), created_date date, last_edited_user char(255), last_edited_date date, SHAPE.STLength() double
    -> _linestring_2 [ArcStroker_Input]
_linestring_2
    GeometryRemover_Output_1 -> AttributeManager_8
AttributeManager_8
    -> linestring [Output00]
swLateral (reader GEODATABASE_SDE_1)
    attributes: OBJECTID integer, COMPKEY integer, ASSETTYPE char(254), SRVTYPE char(254), DESCR char(254), SERVSTAT char(254), OWN char(254), PIPEMATL char(254), PIPELEN double, NOMDIAM double, INTDIAM double, OUTDIAM double, UPNODE char(20), UPSELEV double, DWNNODE char(20), DWNELEV double, CLASS char(254), JTTYPE char(254), MANUFCT char(20), INSTDATE date, ASBUILT char(30), SCHEME char(254), DATA_SRC char(20), COMMENTS char(254), ADDDBY char(20), ADDDTTM date, MODBY char(20), MODDTTM date, CONFIDENCE char(10), CRITICALITY double,
      ALLOCATE range_domain(ALLOCATE_5:integer:0:100), OLDGUID char(40), GlobalID globalid, created_user char(255), created_date date, last_edited_user char(255), last_edited_date date, SHAPE.STLength() double
    -> _linestring [ArcStroker_Input]
_linestring
    GeometryRemover_Output_1 -> AttributeManager_7
AttributeManager_7
    -> linestring [Output]
swChannel (reader GEODATABASE_SDE_1)
    attributes: OBJECTID integer, COMPKEY integer, ASSETTYPE char(254), DESCR char(254), SERVSTAT char(254), OWN char(254), CONMATL char(254), LENGTH double, TPWIDTH double, BSWIDTH double, CHDEPTH double, CHANSHAPE char(254), UPNODE char(20), UPSELEV double, DWNNODE char(20), DWNELEV double, INSTDATE date, ASBUILT char(30), SCHEME char(254), DATA_SRC char(20), COMMENTS char(254), ADDDBY char(20), ADDDTTM date, MODBY char(20), MODDTTM date, CONFIDENCE char(10), CRITICALITY double, ALLOCATE range_domain(ALLOCATE_5:integer:0:100), OLDGUID char(40), GlobalID globalid,
      created_user char(255), created_date date, last_edited_user char(255), last_edited_date date, SHAPE.STLength() double
    -> _linestring_3 [ArcStroker_Input]
_linestring_3
    GeometryRemover_Output_1 -> AttributeManager_9
AttributeManager_9
    -> linestring [Output01]
linestring: FeatureWriter
    CSV2_COORDINATE_SYSTEM_GRANULARITY = FEATURE_TYPE
    CSV2_DELIMITER = ,
    CSV2_ENCODING = UTF-8
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = if_needed
    CSV2_QUALIFY_FIELD_VALUES = if_needed
    CSV2_ROW_TERMINATION = System
    CSV2_TREAT_EMBEDDED_FIELD_QUALIFIERS_AS_UNSAFE = Yes
    CSV2_WRITE_BOM_FOR_UNICODE = Yes
    CSV2_WRITE_FIELD_NAMES = firstrow
    CSV2_WRITE_SCHEMA_FILE = NO
    DATASET = $(FME_MF_DIR_ENCODED)exports
    DATASET_ATTR = _dataset
    FEATURE_TYPE_LIST_ATTR = _feature_types
    FORMAT = CSV2
    TOTAL_FEATURES_WRITTEN_ATTR = _total_features_written

FME custom transformer _polygons_2

GeometryExtractor_Input_1 (input)
    -> GeometryExtractor
GeometryExtractor
    ATTR = point_array
    KIND_LONG = OGC Well Known Text
    OGCVERSION = 1.2
    OGC_WKT_PRECISION_DISPLAY = 64-bit
    REMOVE_GEOMETRY = No
    -> StringReplacer
StringReplacer
    CASE = NO
    FIND_TEXT = POLYGON (
    NO_MATCH = _FME_NO_OP_
    REGEXP = NO
    SRC_ATTRS = point_array
    -> StringReplacer_2
StringReplacer_2
    CASE = NO
    FIND_TEXT = (
    NO_MATCH = _FME_NO_OP_
    REGEXP = NO
    REPLACE_TEXT = {
    SRC_ATTRS = point_array
    -> StringReplacer_3
StringReplacer_3
    CASE = NO
    FIND_TEXT = ))
    NO_MATCH = _FME_NO_OP_
    REGEXP = NO
    REPLACE_TEXT = }
    SRC_ATTRS = point_array
    -> StringReplacer_4
StringReplacer_4
    CASE = NO
    FIND_TEXT = " "
    NO_MATCH = _FME_NO_OP_
    REGEXP = NO
    REPLACE_TEXT = ,
    SRC_ATTRS = point_array
    -> GeometryRemover
GeometryRemover
    REMOVE_COORDSYS = No
    -> GeometryRemover_Output_2 (output)
GeometryRemover_Output_2 (output)

FME custom transformer _nodes

CoordinateExtractor_Input (input)
    -> CoordinateExtractor
CoordinateExtractor
    LIST_NAME = _indices
    MODE = All Coordinates
    -> AttributeCreator
AttributeCreator
    ATTR_TABLE:
      SET_TO x (varchar(200)) = @Value(_indices{0}.x)
      SET_TO y (varchar(200)) = @Value(_indices{0}.y)
    -> GeometryRemover
GeometryRemover
    REMOVE_COORDSYS = No
    -> GeometryRemover_Output (output)
GeometryRemover_Output (output)

FME custom transformer _linestring

ArcStroker_Input (input)
    -> ArcStroker
ArcStroker
    MAKE_POLY = No
    NUM = 0
    STROKE_CHOICE = Number of Interpolated Edges
    STROKED -> GeometryExtractor
GeometryExtractor
    ATTR = point_array
    KIND_LONG = OGC Well Known Text
    OGCVERSION = 1.2
    OGC_WKT_PRECISION_DISPLAY = 64-bit
    REMOVE_GEOMETRY = No
    -> StringReplacer
    <REJECTED> -> GeometryExtractor__Rejected_
StringReplacer
    CASE = NO
    FIND_TEXT = LINESTRING (
    NO_MATCH = _FME_NO_OP_
    REGEXP = NO
    REPLACE_TEXT = {
    SRC_ATTRS = point_array
    -> StringReplacer_2
StringReplacer_2
    CASE = NO
    FIND_TEXT = )
    NO_MATCH = _FME_NO_OP_
    REGEXP = NO
    REPLACE_TEXT = }
    SRC_ATTRS = point_array
    -> StringReplacer_3
StringReplacer_3
    CASE = NO
    FIND_TEXT = " "
    NO_MATCH = _FME_NO_OP_
    REGEXP = NO
    REPLACE_TEXT = ,
    SRC_ATTRS = point_array
    -> GeometryRemover
GeometryRemover
    REMOVE_COORDSYS = No
    -> GeometryRemover_Output_1 (output)
GeometryRemover_Output_1 (output)
GeometryExtractor__Rejected_: Logger
    LOG_FEATURE = LOG_ONLY
    MAXCOORDS = 20
    MAXFEATS = 20
    MESSAGE = Feature is:
    SEVERITY = INFO

FME custom transformer _links
