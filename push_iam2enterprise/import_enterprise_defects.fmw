FME workspace import_enterprise_defects.fmw

Parameters:
- PORTAL = https://qldc.maps.arcgis.com/   # Portal URL

Writers:
- ARCGISPORTALFEATURES_3: ARCGISPORTALFEATURES to $(PORTAL) in NZTM

Bookmark: datetime
Creator
    GEOMTYPE = Geometry Object
    NUM = 1
    CREATED -> DateTimeStamper
DateTimeStamper
    DATETIME_ATTR = origin_utc
    INCLUDE_FRAC_SECONDS = YES
    INCLUDE_OFFSET = NO
    STAMP_TYPE = datetime
    TIMEZONE = utc
    -> AttributeCreator
AttributeCreator
    ATTR_TABLE = SET_TO origin_utc (buffer) = @int(@Value(origin_utc))
    -> Junction_9
Junction_9
    -> Junction_10

Bookmark: extract: cctv surveys spatial and data
Junction_10
    -> FeatureReader [INITIATOR]
FeatureReader
    ATTRIBUTES = "CCTV conduit details","us_node_id,link_suffix,direction,ds_node_id,id,distance,cd,code,diameter,intrusion,percentage,joint,clock_at,clock_to,photo_no,remarks,service_score,structural_score,video_no,video_file,characterisation1,characterisation2,video_no2","CCTV survey","actual_cost,actual_duration,catchment,category_code,CH2MHill_grade,CH2MHill_maint_grade,CH2MHill_maint_score,CH2MHill_score,CH2MHill_struct_grade,CH2MHill_struct_score,comments,completed,contract_no,contractor,current,customer,date_cleaned,date_completed,date_planned,date_started,direction,district,division,ds_node_id,estimated_completion_date,estimated_cost,estimated_duration,finish_cover,finish_depth,finish_invert,finish_manhole,flow_control,gas_detected,grade_to_invert_D,grade_to_invert_U,hard_wired_service_grade,hard_wired_structural_grade,id,index,job_number,lining,lining_type,link_suffix,location,location_details,location_photo,location_photo_ref,location_sketch,location_sketch_ref,long_location,material,mean_score,method,orig_coding,owner,pacp_oandm_index_rating,pacp_oandm_quick_rating,pacp_oandm_rating,pacp_overall_index_rating,pacp_overall_quick_rating,pacp_overall_rating,pacp_struct_index_rating,pacp_struct_quick_rating,pacp_struct_rating,peak_score,photo_reference,photo_storage,pipe_length,pipe_unit_length,place_name,plr,preclean,preclean_choice,purpose,repeat_period,repeat_schedule_number,reverse_setup,rim_to_invert_D,rim_to_invert_U,road_name,schedule_number,service_mean_score,service_override_grade,service_peak_score,service_total_score,shape,sheet_number,size_1,size_2,splitsurvey,splitsurveyref,standard,start_cover,start_depth,start_invert,start_manhole,strategic,structural_override_grade,structural_rating,surveyed_by,surveyed_length,team_leader,temperature,total_length,total_score,uid,us_node_id,use,video_file_in,video_image_loc,video_recorder,vt_no,weather,when_surveyed,year_laid,year_renewed",Pipe,"link_id,access_restrictions,asset_id,backdrop_diam,branch_id,capacity,condition_code,condition_score,consequence_comments,consequence_score,criticality,current_value,date_cleaned,drainage_code,ds_depth_from_cover,ds_height,ds_image_filename,ds_image_ref,ds_invert,ds_lining_material,ds_lining_type,ds_node_id,ds_pipe_material,ds_shape,ds_width,flow_control,gradient,ground_type,ground_water_risk,height,inspection_cost,install_cost,int_pipe_CH2MHill_maint_scr,int_pipe_CH2MHill_scr,int_pipe_CH2MHill_struc_scr,internal_pipe_score,length,lifetime,likelihood_score,lining_material,lining_type,link_suffix,location,mobile_uid,odour_nuisance_risk,owner,pipe_class,pipe_material,pipe_type,property_flooding_risk,rail_business_disruption_risk,rehab_cost,repair_cost,repair_cost_risk,replace_cost,risk_score,security,service_condition_score,shape,site_condition,status,surface_water_risk,survey_date,system_type,taking_off_reference,traffic_delay_risk,traffic_level,uid,unit_length,us_depth_from_cover,us_image_filename,us_image_ref,us_invert,us_node_id,user_date_1,user_date_2,user_date_3,user_date_4,user_date_5,user_number_1,user_number_10,user_number_11,user_number_12,user_number_13,user_number_14,user_number_15,user_number_16,user_number_17,user_number_18,user_number_19,user_number_2,user_number_20,user_number_21,user_number_22,user_number_23,user_number_24,user_number_25,user_number_26,user_number_27,user_number_28,user_number_29,user_number_3,user_number_30,user_number_31,user_number_32,user_number_33,user_number_34,user_number_35,user_number_36,user_number_37,user_number_38,user_number_39,user_number_4,user_number_40,user_number_5,user_number_6,user_number_7,user_number_8,user_number_9,user_text_1,user_text_10,user_text_12,user_text_13,user_text_14,user_text_15,width,year_laid,year_renew"
    ATTR_ACCUM_MODE = Merge Initiator and Result
    ATTR_CONFLICT_RES = Use Result
    ATTR_IGNORE_NULLS = No
    COMBINE_GEOM = Use Result
    DATASET = $(FME_MF_DIR_ENCODED)exports\MIF\*.MIF
    FEATURETYPES = CCTV conduit details
    FORMAT = MIF
    INTERACT = NONE
    MIF_ENCODED_ATTRS = mif_text_string
    MIF_ENCODED_ATTR_NAMES = YES
    MIF_ENCODING = fme-source-encoding
    MIF_PRESERVE_DUPLICATES = YES
    MIF_UNENCODED_ATTR_PREFIX = fme_ mif_
    MIF_USE_SEARCH_ENVELOPE = NO
    ORDER_RESULTS = No
    OUTPUT_FEATURES_DISPLAY = Schema and Data Features
    CCTV conduit details -> Counter_2
    INITIATOR -> FeatureReader_2 [INITIATOR]
FeatureReader_2
    ATTRIBUTES = CSV,"id,video_no,photo_no,distance,cd,code,video_file,diameter,Joint,clock_at,clock_to,percentage,intrusion,remarks,characterisation1,characterisation2,detail_image,video_no2,service_score,structural_score,characterisation3"
    ATTR_ACCUM_MODE = Merge Initiator and Result
    ATTR_CONFLICT_RES = Use Result
    ATTR_IGNORE_NULLS = No
    COMBINE_GEOM = Use Result
    CSV2_CASE_SENSITIVE_FIELD_NAMES = Yes
    CSV2_CHUNK_SIZE = 100000
    CSV2_DATA_START_LINE = 2
    CSV2_DATE_INPUT_FORMAT = ISO
    CSV2_DELIMITER = auto
    CSV2_DELIMITER_DETECTION_ALGORITHM = EQUAL_FIELDS_PER_LINE
    CSV2_ENCODING = windows-1252
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = No
    CSV2_SCAN_ADDITIONAL_FIELDS = No
    CSV2_SCAN_MAX_ROWS = 250000
    CSV2_SCAN_TYPES = Yes
    CSV2_SKIP_DUPLICATE_DELIMITERS = No
    CSV2_STRING_TYPE_ATTRIBUTE_HANDLING = EXPLICIT_WIDTH
    CSV2_SUPPORTED_READER_ARCHIVE_EXTENSIONS = csv.gz,txt.gz
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_TYPE_ATTRIBUTE_HANDLING = STANDARD_TYPES
    CSV2_USE_CUSTOM_SCHEMA = NO
    DATASET = $(FME_MF_DIR_ENCODED)exports\CSV\network.csv_cams_cctv_survey_details.csv
    FORMAT = CSV2
    INTERACT = NONE
    ORDER_RESULTS = No
    OUTPUT_FEATURES_DISPLAY = Schema and Data Features
    CSV -> Counter
Counter
    CNT_ATTR = _count_2
    SCOPE = Local
    START = 0
    -> Junction_3
Junction_3
    -> Junction_4
Counter_2
    CNT_ATTR = _count_1
    SCOPE = Local
    START = 0
    -> Junction
Junction
    -> Junction_2

Bookmark: transform: spatial join of data to CSV file
Junction_4
    -> FeatureMerger [SUPPLIER]
Junction_2
    -> AttributeKeeper
AttributeKeeper
    CREATE_BULK_MODE_FEATURES = NO
    KEEP_ATTRS = _count_1,id
    -> FeatureMerger [REQUESTOR]
FeatureMerger
    ATTR_ACCUM_MODE = Merge Supplier
    ATTR_CONFLICT_RES = Use Requestor
    IGNORE_NULLS = No
    JOIN_KEYS = @Value(_count_1) @Value(_count_2) AUTO
    MERGE_TYPE = Attributes Only
    PROCESS_DUPS = NO
    REJECT_NULL_MISSING_KEYS = No
    SUPPLIERS_FIRST = No
    MERGED -> AttributeRemover
AttributeRemover
    REMOVE_ATTRS = _count_1,_count_2,_creation_instance,_matched_records
    -> Junction_5
Junction_5
    -> Junction_6

Bookmark: validation: code
Junction_6
    -> UniqueValueLogger_4
    -> AttributeValueMapper
UniqueValueLogger_4
    VAL = @Value(code)
    -> Sorter
Sorter
    SORT_PARM = _value NATURAL ASCENDING
AttributeValueMapper
    DEFAULT_VALUE = @Value(code)
    LUT = -,FME_NULL_VALUE,#N/A,FME_NULL_VALUE
    MAPPING_DIRECTION = FORWARD
    SRC = code
    VAL_ATTR = code
    -> AttributeCreator_2
AttributeCreator_2
    ATTR_TABLE = SET_TO code (varchar(5)) = @UpperCase(@Value(code))
    -> Junction_7
Junction_7
    -> Junction_8

Bookmark: validation: cd
Junction_8
    -> UniqueValueLogger_5
    -> Junction_11
UniqueValueLogger_5
    VAL = @Value(cd)
    -> Sorter_2
Sorter_2
    SORT_PARM = _value NATURAL ASCENDING
Junction_11
    -> Junction_12

Bookmark: validation: distance
Junction_12
    -> Tester
    -> Junction_13
Tester
    BOOL_OP = OR
    TEST_CLAUSE:
      TEST distance ATTRIBUTE_IS_MISSING ""
      TEST distance ATTRIBUTE_IS_EMPTY ""
      TEST distance ATTRIBUTE_VALUE_NULL ""
    TEST_MODE = TEST
Junction_13
    -> Junction_14

Bookmark: load: 2 agol
Junction_14
    -> cctv_survey_defects (writer ARCGISPORTALFEATURES_3)
cctv_survey_defects (writer ARCGISPORTALFEATURES_3)
    attributes: id String, video_no Double, photo_no String, distance Double, cd String, code String, video_file String, diameter Double, Joint Integer, clock_at Integer, clock_to Integer, percentage Double, remarks String, intrusion String, characterisation1 String, characterisation2 String, video_no2 String, detail_image String, service_score Double, structural_score Double, characterisation3 String, origin_utc Date

FME custom transformer UniqueValueLogger
Description
This transformer lists all of the unique values for a chosen attribute alongside  a count attribute of the number of occurrences of each of these values. The information is logged in both the Translation Window / Workspace log file, and stored in attributes.
This transformer is useful when you are creating a workspace and need to know the possible values to use in a filter.
Input Ports
Input: This transformer accepts any features with an attribute.
Output Ports
Output: Features are output with the attribute selected as the unique value to filter, and a new attribute containing the number of occurrences of each unique value. All other attributes are removed. 
_count: Number of occurrences of each unique value.
_value: Unique values of selected attribute.
Parameters
Attribute to Analyze: Select the attribute for the transformer to run analysis on. 
Notes
Transformer alternatives:
Duplicate Filter - Consider using this transformer if you are looking to get a list of unique values and do not need a _count attribute 
StatisticsCalculator - Setting the Group By mode to the attribute to analyze will produce the same result as this transformer, it may beuse If you would like to gather other statistics as well as count of the unique attributes.

Parameters:
- VAL =   # Attribute to Analyze

Input (input)
    -> AttributeCreator

Bookmark: Count unique attribute values
AttributeCreator
    ATTR_TABLE = SET_TO _value = $(VAL)
    -> AttributeKeeper
Note: Remove unwanted / attributes
AttributeKeeper
    CREATE_BULK_MODE_FEATURES = No
    KEEP_ATTRS = _value
    -> Aggregator
Note: Create aggregates of / features, grouped by / the target attribute value
Aggregator
    ACCUM_ATTRS_NAME = Merge Incoming Attributes
    AGGREGATE_TYPE = Homogeneous Collection (If Possible)
    COUNT_ATTR = _count
    GROUP_BY = _value
    MODE = Geometry - Assemble One Level
    SEP = ,
    AGGREGATE -> StringConcatenator
Note: Concatenate unique values / with their occurrence counts
StringConcatenator
    ACTION = Create New Attribute
    PARM_LINE = fme_basicstring:14%1%14%1:@Value(_value),@Value(_count)
    VAL_ATTR = _concatenated
    -> Sorter
Note: Sort output based on / occurrence count and / attribute value
Sorter
    SORT_PARM = _count NUMERIC DESCENDING _value ALPHA ASCENDING
    SORTED -> ListBuilder
    SORTED -> AttributeManager

Bookmark: Create output
AttributeManager
    ATTR_TABLE = REMOVE _concatenated
    -> Output (output)
Output (output)

Bookmark: Log unique attribute values
Note: Turn all input features / Into a single list
ListBuilder
    LIST_NAME = _list
    -> ListConcatenator
Note: Concatenate values of / the list into an attribute
ListConcatenator
    DROP_EMPTY_PARTS = No
    LIST_ATTR = _list{}._concatenated
    VAL_ATTR = UNIQUE VALUES
    -> StringConcatenator_2
Note: Add header
StringConcatenator_2
    ACTION = Create New Attribute
    PARM_LINE = "\n\nVALUE, COUNT\n@Value(UNIQUE VALUES)\n"
    VAL_ATTR = UNIQUE VALUES
    -> AttributeRemover_2
Note: Remote the list
AttributeRemover_2
    LIST_ATTRS = _list{}
    -> Logger
Note: Log the single feature / that contains the / output attribute
Logger
    LOG_FEATURE = LOG_RECORD
    MAXCOORDS = 1
    MAXFEATS = 1
    MESSAGE = Unique values:
    SEVERITY = INFO
