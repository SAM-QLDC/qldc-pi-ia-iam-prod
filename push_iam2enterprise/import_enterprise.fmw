FME workspace import_enterprise.fmw

Parameters:
- PORTAL = https://qldc.maps.arcgis.com/   # Portal URL

Writers:
- ARCGISPORTALFEATURES_1: ARCGISPORTALFEATURES to $(PORTAL) in NZTM
- ARCGISPORTALFEATURES_2: ARCGISPORTALFEATURES to $(PORTAL) in NZTM
- ARCGISPORTALFEATURES_3: ARCGISPORTALFEATURES to $(PORTAL) in NZTM

Note: process a littel dumb ... could be improved by only updating changed data

Bookmark: datetime
Creator
    GEOMTYPE = Geometry Object
    NUM = 1
    CREATED -> DateTimeStamper
DateTimeStamper
    DATETIME_ATTR = origin_utc
    INCLUDE_FRAC_SECONDS = YES
    STAMP_TYPE = date
    TIMEZONE = utc
    -> AttributeCreator
AttributeCreator
    ATTR_TABLE = SET_TO origin_utc (buffer) = @int(@Value(origin_utc))
    -> Junction_9
Junction_9
    -> Junction_10

Bookmark: extract: mid/mif files
Junction_10
    -> FeatureReader [INITIATOR]
FeatureReader
    ATTRIBUTES = "CCTV conduit details","us_node_id,link_suffix,direction,ds_node_id,id,distance,cd,code,diameter,intrusion,percentage,joint,clock_at,clock_to,photo_no,remarks,service_score,structural_score,video_no,video_file,characterisation1,characterisation2,video_no2","CCTV survey","actual_cost,actual_duration,catchment,category_code,CH2MHill_grade,CH2MHill_maint_grade,CH2MHill_maint_score,CH2MHill_score,CH2MHill_struct_grade,CH2MHill_struct_score,comments,completed,contract_no,contractor,current,customer,date_cleaned,date_completed,date_planned,date_started,direction,district,division,ds_node_id,estimated_completion_date,estimated_cost,estimated_duration,finish_cover,finish_depth,finish_invert,finish_manhole,flow_control,gas_detected,grade_to_invert_D,grade_to_invert_U,hard_wired_service_grade,hard_wired_structural_grade,id,index,job_number,lining,lining_type,link_suffix,location,location_details,location_photo,location_photo_ref,location_sketch,location_sketch_ref,long_location,material,mean_score,method,orig_coding,owner,pacp_oandm_index_rating,pacp_oandm_quick_rating,pacp_oandm_rating,pacp_overall_index_rating,pacp_overall_quick_rating,pacp_overall_rating,pacp_struct_index_rating,pacp_struct_quick_rating,pacp_struct_rating,peak_score,photo_reference,photo_storage,pipe_length,pipe_unit_length,place_name,plr,preclean,preclean_choice,purpose,repeat_period,repeat_schedule_number,reverse_setup,rim_to_invert_D,rim_to_invert_U,road_name,schedule_number,service_mean_score,service_override_grade,service_peak_score,service_total_score,shape,sheet_number,size_1,size_2,splitsurvey,splitsurveyref,standard,start_cover,start_depth,start_invert,start_manhole,strategic,structural_override_grade,structural_rating,surveyed_by,surveyed_length,team_leader,temperature,total_length,total_score,uid,us_node_id,use,video_file_in,video_image_loc,video_recorder,vt_no,weather,when_surveyed,year_laid,year_renewed",Pipe,"link_id,access_restrictions,asset_id,backdrop_diam,branch_id,capacity,condition_code,condition_score,consequence_comments,consequence_score,criticality,current_value,date_cleaned,drainage_code,ds_depth_from_cover,ds_height,ds_image_filename,ds_image_ref,ds_invert,ds_lining_material,ds_lining_type,ds_node_id,ds_pipe_material,ds_shape,ds_width,flow_control,gradient,ground_type,ground_water_risk,height,inspection_cost,install_cost,int_pipe_CH2MHill_maint_scr,int_pipe_CH2MHill_scr,int_pipe_CH2MHill_struc_scr,internal_pipe_score,length,lifetime,likelihood_score,lining_material,lining_type,link_suffix,location,mobile_uid,odour_nuisance_risk,owner,pipe_class,pipe_material,pipe_type,property_flooding_risk,rail_business_disruption_risk,rehab_cost,repair_cost,repair_cost_risk,replace_cost,risk_score,security,service_condition_score,shape,site_condition,status,surface_water_risk,survey_date,system_type,taking_off_reference,traffic_delay_risk,traffic_level,uid,unit_length,us_depth_from_cover,us_image_filename,us_image_ref,us_invert,us_node_id,user_date_1,user_date_2,user_date_3,user_date_4,user_date_5,user_number_1,user_number_10,user_number_11,user_number_12,user_number_13,user_number_14,user_number_15,user_number_16,user_number_17,user_number_18,user_number_19,user_number_2,user_number_20,user_number_21,user_number_22,user_number_23,user_number_24,user_number_25,user_number_26,user_number_27,user_number_28,user_number_29,user_number_3,user_number_30,user_number_31,user_number_32,user_number_33,user_number_34,user_number_35,user_number_36,user_number_37,user_number_38,user_number_39,user_number_4,user_number_40,user_number_5,user_number_6,user_number_7,user_number_8,user_number_9,user_text_1,user_text_10,user_text_12,user_text_13,user_text_14,user_text_15,width,year_laid,year_renew"
    ATTR_ACCUM_MODE = Merge Initiator and Result
    ATTR_CONFLICT_RES = Use Result
    ATTR_IGNORE_NULLS = No
    COMBINE_GEOM = Use Result
    DATASET = $(FME_MF_DIR_ENCODED)exports\MIF\*.MIF
    FEATURETYPES = CCTV conduit details CCTV survey Pipe
    FORMAT = MIF
    INTERACT = NONE
    MIF_ENCODED_ATTRS = mif_text_string
    MIF_ENCODED_ATTR_NAMES = YES
    MIF_ENCODING = fme-source-encoding
    MIF_PRESERVE_DUPLICATES = YES
    MIF_UNENCODED_ATTR_PREFIX = fme_ mif_
    MIF_USE_SEARCH_ENVELOPE = NO
    ORDER_RESULTS = No
    OUTPUT_FEATURES_DISPLAY = Schema and Data Features
    CCTV conduit details -> Junction_7
    CCTV survey -> Junction_3
    Pipe -> Junction_5
Junction_5
    -> Junction_6
Junction_3
    -> Junction_4
Junction_7
    -> Junction_8

Bookmark: transform: data
Junction_6
    -> GeometryExtractor_2
GeometryExtractor_2
    ATTR = _geometry
    KIND_LONG = OGC Well Known Text
    OGCVERSION = 1.2
    OGC_WKT_PRECISION_DISPLAY = 64-bit
    REMOVE_GEOMETRY = No
    -> BulkAttributeRemover
    <REJECTED> -> GeometryExtractor_2_Output
BulkAttributeRemover
    ATTR_EXP = ^user_
    -> AttributeManager_2
AttributeManager_2
    ATTR_TABLE:
      REMOVE _creation_instance (uint64)
      REMOVE _geometry (buffer)
    -> DateTimeConverter_2
DateTimeConverter_2
    DATETIME_ATTR = survey_date year_laid year_renew
    IN_FORMAT = %N/%e/%Y
    OUT_FORMAT = %Y%m%d
    PASSTHROUGH = NO
    REPAIR_INPUT = YES
    -> AttributeManager_4
    <REJECTED> -> AttributeManager_4
AttributeManager_4
    ATTR_TABLE:
      RENAME_SET_VALUE length > conduit_length (real64)
      RENAME_SET_VALUE shape > conduit_shape (varchar(10))
    -> Junction_11
Junction_11
    -> Junction_12
GeometryExtractor_2_Output: Logger
    LOG_FEATURE = LOG_ONLY
    MAXCOORDS = 20
    MAXFEATS = 20
    MESSAGE = Feature is:
    SEVERITY = INFO
Junction_4
    -> GeometryExtractor
GeometryExtractor
    ATTR = _geometry
    KIND_LONG = OGC Well Known Text
    OGCVERSION = 1.2
    OGC_WKT_PRECISION_DISPLAY = 64-bit
    REMOVE_GEOMETRY = No
    -> AttributeManager
    <REJECTED> -> GeometryExtractor__Rejected_
AttributeManager
    ATTR_TABLE:
      REMOVE _creation_instance (uint64)
      REMOVE surveyed_by (varchar(25))
      REMOVE actual_cost (real64)
      REMOVE actual_duration (real64)
      REMOVE catchment (varchar(30))
      REMOVE category_code (varchar(3))
      REMOVE CH2MHill_grade (varchar(2))
      REMOVE CH2MHill_maint_grade (varchar(2))
      REMOVE CH2MHill_maint_score (real64)
      REMOVE CH2MHill_score (real64)
      REMOVE CH2MHill_struct_grade (varchar(2))
      REMOVE CH2MHill_struct_score (real64)
      REMOVE comments (varchar(255))
      REMOVE completed (logical)
      REMOVE contract_no (varchar(100))
      REMOVE contractor (varchar(32))
      REMOVE customer (varchar(40))
      REMOVE date_cleaned (varchar(64))
      REMOVE date_completed (varchar(64))
      REMOVE date_planned (varchar(64))
      REMOVE date_started (datetime)
      REMOVE district (varchar(200))
      REMOVE division (varchar(255))
      REMOVE estimated_completion_date (varchar(64))
      REMOVE estimated_cost (real64)
      REMOVE estimated_duration (real64)
      REMOVE finish_cover (real64)
      REMOVE finish_depth (real64)
      REMOVE finish_invert (real64)
      REMOVE flow_control (varchar(25))
      REMOVE gas_detected (logical)
      REMOVE grade_to_invert_D (real64)
      REMOVE grade_to_invert_U (real64)
      REMOVE index (int32)
      REMOVE job_number (varchar(15))
      REMOVE lining (varchar(10))
      REMOVE lining_type (varchar(30))
      REMOVE location (varchar(100))
      REMOVE location_details (varchar(255))
      REMOVE location_photo (varchar(50))
      REMOVE location_photo_ref (varchar(30))
      REMOVE location_sketch (varchar(50))
      REMOVE location_sketch_ref (varchar(30))
      REMOVE long_location (real64)
      REMOVE material (varchar(64))
      REMOVE owner (varchar(64))
      REMOVE pacp_oandm_index_rating (real64)
      REMOVE pacp_oandm_quick_rating (varchar(6))
      REMOVE pacp_oandm_rating (int32)
      REMOVE pacp_overall_index_rating (real64)
      REMOVE pacp_overall_quick_rating (varchar(6))
      REMOVE pacp_overall_rating (int32)
      REMOVE pacp_struct_index_rating (real64)
      REMOVE pacp_struct_quick_rating (varchar(6))
      REMOVE pacp_struct_rating (int32)
      REMOVE photo_reference (varchar(200))
      REMOVE photo_storage (varchar(1))
      REMOVE pipe_unit_length (real64)
      REMOVE place_name (varchar(64))
      REMOVE preclean (logical)
      REMOVE preclean_choice (varchar(15))
      REMOVE purpose (varchar(64))
      REMOVE repeat_period (varchar(20))
      REMOVE repeat_schedule_number (varchar(40))
      REMOVE reverse_setup (int32)
      REMOVE rim_to_invert_D (real64)
      REMOVE rim_to_invert_U (real64)
      REMOVE road_name (varchar(64))
      REMOVE schedule_number (varchar(40))
      REMOVE shape (varchar(15))
      REMOVE sheet_number (int32)
      REMOVE size_1 (real64)
      REMOVE size_2 (real64)
      REMOVE start_cover (real64)
      REMOVE start_depth (real64)
      REMOVE start_invert (real64)
      REMOVE strategic (varchar(30))
      REMOVE team_leader (varchar(40))
      REMOVE temperature (varchar(3))
      REMOVE use (varchar(15))
      REMOVE video_file_in (varchar(255))
      REMOVE video_recorder (varchar(255))
      REMOVE vt_no (varchar(5))
      REMOVE weather (varchar(12))
      REMOVE year_laid (varchar(9))
      REMOVE year_renewed (int32)
      REMOVE _geometry (buffer)
    -> DateTimeConverter
DateTimeConverter
    DATETIME_ATTR = when_surveyed
    IN_FORMAT = %N/%e/%Y
    OUT_FORMAT = %Y%m%d
    PASSTHROUGH = NO
    REPAIR_INPUT = YES
    -> Junction
    <REJECTED> -> Junction
Junction
    -> Junction_2
GeometryExtractor__Rejected_: Logger
    LOG_FEATURE = LOG_ONLY
    MAXCOORDS = 20
    MAXFEATS = 20
    MESSAGE = Feature is:
    SEVERITY = INFO
Junction_8
    -> GeometryExtractor_3
GeometryExtractor_3
    ATTR = _geometry
    KIND_LONG = OGC Well Known Text
    OGCVERSION = 1.2
    OGC_WKT_PRECISION_DISPLAY = 64-bit
    REMOVE_GEOMETRY = No
    -> AttributeManager_3
    <REJECTED> -> GeometryExtractor_3_Output
AttributeManager_3
    ATTR_TABLE:
      REMOVE _geometry (buffer)
      REMOVE _creation_instance (uint64)
    -> CoordinateExtractor
CoordinateExtractor
    LIST_NAME = _indices
    MODE = All Coordinates
    -> AttributeCreator_2
AttributeCreator_2
    ATTR_TABLE:
      SET_TO x (real64) = @Value(_indices{0}.x)
      SET_TO y (real64) = @Value(_indices{0}.y)
      SET_TO distance2 (varchar(200)) = @double(@Substring(@Value(distance),1,@StringLength(@Value(distance))-3))
    -> Junction_13
Junction_13
    -> Junction_14
GeometryExtractor_3_Output: Logger
    LOG_FEATURE = LOG_ONLY
    MAXCOORDS = 20
    MAXFEATS = 20
    MESSAGE = Feature is:
    SEVERITY = INFO

Bookmark: load: 2 agol
Junction_12
    -> pipe (writer ARCGISPORTALFEATURES_2)
pipe (writer ARCGISPORTALFEATURES_2)
    attributes: link_id String, access_restrictions String, asset_id String, backdrop_diam Double, branch_id Integer, capacity Double, condition_code String, condition_score Integer, consequence_comments String, consequence_score Double, criticality String, current_value Double, date_cleaned String, drainage_code String, ds_depth_from_cover Double, ds_height Double, ds_image_filename String, ds_image_ref String, ds_invert Double, ds_lining_material String, ds_lining_type String, ds_node_id String, ds_pipe_material String, ds_shape String, ds_width Double, flow_control String, gradient Double, ground_type String, ground_water_risk Double, height Double,
      inspection_cost Double, install_cost Double, int_pipe_CH2MHill_maint_scr Integer, int_pipe_CH2MHill_scr Integer, int_pipe_CH2MHill_struc_scr Integer, internal_pipe_score Integer, conduit_length Double, lifetime Integer, likelihood_score Double, lining_material String, lining_type String, link_suffix String, location String, mobile_uid String, odour_nuisance_risk Double, owner String, pipe_class String, pipe_material String, pipe_type String, property_flooding_risk Double, rail_business_disruption_risk Double, rehab_cost Double, repair_cost Double, repair_cost_risk Double, replace_cost Double, risk_score Double, security String, service_condition_score Integer, conduit_shape String, site_condition String,
      status String, surface_water_risk Double, survey_date Date, system_type String, taking_off_reference String, traffic_delay_risk Double, traffic_level Double, uid String, unit_length Double, us_depth_from_cover Double, us_image_filename String, us_image_ref String, us_invert Double, us_node_id String, width Double, year_laid Date, year_renew Date, origin_utc Date
Junction_2
    -> cctv_survey (writer ARCGISPORTALFEATURES_1)
cctv_survey (writer ARCGISPORTALFEATURES_1)
    attributes: id String, uid String, start_manhole String, finish_manhole String, direction String, splitsurvey String, splitsurveyref String, current String, us_node_id String, ds_node_id String, link_suffix String, standard String, orig_coding String, hard_wired_service_grade Double, hard_wired_structural_grade Double, mean_score Double, method String, peak_score Double, pipe_length Double, plr String, service_mean_score Double, service_override_grade Double, service_peak_score Double, service_total_score Double, structural_override_grade Double, structural_rating Double, surveyed_length Double, total_length Double, total_score Double, video_image_loc String,
      when_surveyed Date, origin_utc Date
Junction_14
    -> cctv_survey_defects (writer ARCGISPORTALFEATURES_3)
cctv_survey_defects (writer ARCGISPORTALFEATURES_3)
    attributes: us_node_id String, link_suffix String, direction String, ds_node_id String, id String, distance Double, cd String, code String, diameter Double, intrusion Double, percentage Double, joint SmallInteger, clock_at Integer, clock_to Integer, photo_no Integer, remarks String, service_score Integer, structural_score Integer, video_no String, video_file String, characterisation1 String, characterisation2 String, video_no2 String, origin_utc Date
