FME workspace A distribution - import gis.fmw

Parameters:
- water_type = 1
- dir = $(FME_MF_DIR)exports\water supply CSV   # Folder

Bookmark: datetime
Creator
    GEOMTYPE = Geometry Object
    NUM = 1
    CREATED -> DateTimeStamper
DateTimeStamper
    DATETIME_ATTR = origin_utc
    INCLUDE_FRAC_SECONDS = NO
    INCLUDE_OFFSET = NO
    STAMP_TYPE = datetime
    TIMEZONE = utc
    -> Junction_23
Junction_23
    -> Junction_24

Bookmark: extract: three waters data from AGOL
Junction_24
    -> FeatureReader_2 [INITIATOR]
    -> FeatureReader [INITIATOR]
FeatureReader_2
    ARCGISONLINEFEATURES_CREATE_FEATURE_TABLES_FROM_DATA = Yes
    ARCGISONLINEFEATURES_FEATURESERVICE = Queenstown Lakes District Council Open Data/Three Waters Assets(a99d1860d32f44fbb025142a364d0458)
    ARCGISONLINEFEATURES_FEATURES_PER_REQUEST = 1000
    ARCGISONLINEFEATURES_FORMAT_GUID = YES
    ARCGISONLINEFEATURES_NC = hywell Esri ArcGIS Online
    ARCGISONLINEFEATURES_QUERY_FEATURE_TYPES_FOR_MERGE_FILTERS = Yes
    ARCGISONLINEFEATURES_RESOLVE_DOMAINS = No
    ARCGISONLINEFEATURES_USE_SEARCH_ENVELOPE = NO
    ATTRIBUTES = "Stormwater Channel","OBJECTID,COMPKEY,ASSETTYPE,DESCR,SERVSTAT,OWN,CONMATL,LENGTH,TPWIDTH,BSWIDTH,CHDEPTH,CHANSHAPE,UPNODE,UPSELEV,DWNNODE,DWNELEV,INSTDATE,ASBUILT,SCHEME,DATA_SRC,COMMENTS,ADDDBY,ADDDTTM,MODBY,MODDTTM,CONFIDENCE,CRITICALITY,GlobalID,created_user,created_date,last_edited_user,last_edited_date,Shape__Length","Stormwater Inlet","OBJECTID,COMPKEY,ASSETTYPE,DESCR,SERVSTAT,OWN,ZCOORD,INVERTELEV,CVRTYPE,MANUFCT,INSTDATE,ASBUILT,SCHEME,DATA_SRC,COMMENTS,ADDDBY,ADDDTTM,MODBY,MODDTTM,CONFIDENCE,CRITICALITY,GlobalID,created_user,created_date,last_edited_user,last_edited_date","Stormwater Lateral","OBJECTID,COMPKEY,ASSETTYPE,SRVTYPE,DESCR,SERVSTAT,OWN,PIPEMATL,PIPELEN,NOMDIAM,INTDIAM,OUTDIAM,UPNODE,UPSELEV,DWNNODE,DWNELEV,CLASS,JTTYPE,MANUFCT,INSTDATE,ASBUILT,SCHEME,DATA_SRC,COMMENTS,ADDDBY,ADDDTTM,MODBY,MODDTTM,CONFIDENCE,CRITICALITY,GlobalID,created_user,created_date,last_edited_user,last_edited_date,Shape__Length","Stormwater Main","OBJECTID,COMPKEY,ASSETTYPE,DESCR,SERVSTAT,OWN,PIPEMATL,PIPELEN,NOMDIAM,INTDIAM,OUTDIAM,UPNODE,UPSELEV,DWNNODE,DWNELEV,CLASS,JTTYPE,MANUFCT,INSTMTHD,INSTDATE,LINEMATL,LINEDATE,LINEMTHD,ASBUILT,SCHEME,DATA_SRC,COMMENTS,ADDDBY,ADDDTTM,MODBY,MODDTTM,CONFIDENCE,CRITICALITY,GlobalID,created_user,created_date,last_edited_user,last_edited_date,Shape__Length","Stormwater Manhole","OBJECTID,COMPKEY,ASSETTYPE,DESCR,SERVSTAT,OWN,ZCOORD,INVERTELEV,BARLSHAPE,BARLDIAM,BARLDIM2,CHAMATL,CVRDIAM,CVRTYPE,MANUFCT,INSTDATE,ASBUILT,SCHEME,DATA_SRC,COMMENTS,ADDDBY,ADDDTTM,MODBY,MODDTTM,CONFIDENCE,CRITICALITY,GlobalID,created_user,created_date,last_edited_user,last_edited_date","Stormwater Meter","OBJECTID,COMPKEY,ASSETTYPE,DESCR,SERVSTAT,OWN,ZCOORD,INVERTELEV,METERSZ,SERNO,MODELNO,INSTDATE,ASBUILT,SCHEME,DATA_SRC,COMMENTS,ADDDBY,ADDDTTM,MODBY,MODDTTM,CONFIDENCE,CRITICALITY,GlobalID,created_user,created_date,last_edited_user,last_edited_date","Stormwater Node","OBJECTID,COMPKEY,ASSETTYPE,DESCR,SERVSTAT,OWN,ZCOORD,INVERTELEV,INSTDATE,ASBUILT,SCHEME,DATA_SRC,COMMENTS,ADDDBY,ADDDTTM,MODBY,MODDTTM,CONFIDENCE,CRITICALITY,GlobalID,created_user,created_date,last_edited_user,last_edited_date","Stormwater Pumpstation","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,GlobalID,created_user,created_date,last_edited_user,last_edited_date,Shape__Area,Shape__Length","Stormwater Structure","OBJECTID,COMPKEY,ASSETTYPE,DESCR,SERVSTAT,OWN,ZCOORD,MANUFCT,INSTDATE,ASBUILT,SCHEME,DATA_SRC,COMMENTS,ADDDBY,ADDDTTM,MODBY,MODDTTM,CONFIDENCE,CRITICALITY,GlobalID,created_user,created_date,last_edited_user,last_edited_date","Stormwater Treatment Device","OBJECTID,COMPKEY,ASSETTYPE,DESCR,SERVSTAT,OWN,ZCOORD,INVERTELEV,DEVCAREA,BARLDIAM,BARLDIM2,DVCMATL,CVRDIAM,CVRTYPE,MANUFCT,INSTDATE,ASBUILT,SCHEME,DATA_SRC,COMMENTS,ADDDBY,ADDDTTM,MODBY,MODDTTM,CONFIDENCE,CRITICALITY,GlobalID,created_user,created_date,last_edited_user,last_edited_date,VOIDMAT","Stormwater Treatment Device Area","OBJECTID,COMPKEYREF,COMMENTS,ADDDBY,ADDDTTM,MODBY,MODDTTM,GlobalID,created_user,created_date,last_edited_user,last_edited_date,Shape__Area,Shape__Length","Stormwater Valve","OBJECTID,COMPKEY,ASSETTYPE,DESCR,SERVSTAT,OWN,ZCOORD,INVERTELEV,VALVESTAT,VALVESZ,SERNO,MODELNO,MANUFCT,INSTDATE,ASBUILT,SCHEME,DATA_SRC,COMMENTS,ADDDBY,ADDDTTM,MODBY,MODDTTM,CONFIDENCE,CRITICALITY,GlobalID,created_user,created_date,last_edited_user,last_edited_date","Wastewater Lateral","OBJECTID,COMPKEY,ASSETTYPE,SRVTYPE,DESCR,SERVSTAT,OWN,PIPEMATL,PIPELEN,NOMDIAM,INTDIAM,OUTDIAM,CLASS,MANUFCT,INSTDATE,ASBUILT,SCHEME,DATA_SRC,COMMENTS,ADDDBY,ADDDTTM,MODBY,MODDTTM,CONFIDENCE,CRITICALITY,GlobalID,created_user,created_date,last_edited_user,last_edited_date,Shape__Length","Wastewater Main","OBJECTID,COMPKEY,ASSETTYPE,DESCR,SERVSTAT,OWN,PIPEMATL,PIPELEN,NOMDIAM,INTDIAM,OUTDIAM,UPNODE,UPSELEV,DWNNODE,DWNELEV,CLASS,INSTDATE,JTTYPE,MANUFCT,INSTMTHD,LINEMATL,LINEMTHD,LINEDATE,ASBUILT,SCHEME,DATA_SRC,COMMENTS,ADDDBY,ADDDTTM,MODBY,MODDTTM,CONFIDENCE,CRITICALITY,GlobalID,created_user,created_date,last_edited_user,last_edited_date,Shape__Length","Wastewater Manhole","OBJECTID,COMPKEY,ASSETTYPE,SUBTYPE,DESCR,SERVSTAT,OWN,ZCOORD,INVERTELEV,BARLSHAPE,BARLDIAM,BARLDIM2,CHAMATL,CVRTYPE,CVRDIAM,MANUFCT,INSTDATE,ASBUILT,SCHEME,DATA_SRC,COMMENTS,ADDDBY,ADDDTTM,MODBY,MODDTTM,CONFIDENCE,CRITICALITY,GlobalID,created_user,created_date,last_edited_user,last_edited_date","Wastewater Meter","OBJECTID,COMPKEY,ASSETTYPE,DESCR,SERVSTAT,OWN,ZCOORD,INVERTELEV,METERSZ,SERNO,MODELNO,MANUFCT,INSTDATE,ASBUILT,SCHEME,DATA_SRC,COMMENTS,ADDDBY,ADDDTTM,MODBY,MODDTTM,CONFIDENCE,CRITICALITY,GlobalID,created_user,created_date,last_edited_user,last_edited_date","Wastewater Node","OBJECTID,COMPKEY,ASSETTYPE,DESCR,SERVSTAT,OWN,ZCOORD,INVERTELEV,INSTDATE,ASBUILT,SCHEME,DATA_SRC,COMMENTS,ADDDBY,ADDDTTM,MODBY,MODDTTM,CONFIDENCE,CRITICALITY,GlobalID,created_user,created_date,last_edited_user,last_edited_date","Wastewater Pumpstation","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,created_user,created_date,last_edited_user,last_edited_date,GlobalID,Shape__Area,Shape__Length","Wastewater Treatment Plant","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,created_user,created_date,last_edited_user,last_edited_date,GlobalID,Shape__Area,Shape__Length","Wastewater Valve","OBJECTID,COMPKEY,ASSETTYPE,DESCR,SERVSTAT,OWN,ZCOORD,INVERTELEV,VALVESTAT,VALVESZ,SERNO,MODELNO,MANUFCT,INSTDATE,ASBUILT,SCHEME,DATA_SRC,COMMENTS,ADDDBY,ADDDTTM,MODBY,MODDTTM,CONFIDENCE,CRITICALITY,GlobalID,created_user,created_date,last_edited_user,last_edited_date","Water Supply Backflow","OBJECTID,COMPKEY,ASSETTYPE,DESCR,SERVSTAT,OWN,ZCOORD,INVERTELEV,VALVESTAT,VALVESZ,SERNO,MODELNO,MANUFCT,INSTDATE,ASBUILT,SCHEME,DATA_SRC,COMMENTS,ADDDBY,ADDDTTM,MODBY,MODDTTM,CONFIDENCE,CRITICALITY,GlobalID,created_user,created_date,last_edited_user,last_edited_date","Water Supply Hydrant","OBJECTID,COMPKEY,ASSETTYPE,DESCR,SERVSTAT,OWN,ZCOORD,INVERTELEV,MODELNO,MANUFCT,INSTDATE,ASBUILT,SCHEME,DATA_SRC,COMMENTS,ADDDBY,ADDDTTM,MODBY,MODDTTM,CONFIDENCE,CRITICALITY,GlobalID,created_user,created_date,last_edited_user,last_edited_date","Water Supply Lateral","OBJECTID,COMPKEY,ASSETTYPE,SRVTYPE,DESCR,SERVSTAT,OWN,PIPEMATL,PIPELEN,NOMDIAM,INTDIAM,OUTDIAM,CLASS,MANUFCT,INSTDATE,ASBUILT,SCHEME,DATA_SRC,COMMENTS,ADDDBY,ADDDTTM,MODBY,MODDTTM,CONFIDENCE,CRITICALITY,GlobalID,created_user,created_date,last_edited_user,last_edited_date,Shape__Length","Water Supply Main","OBJECTID,COMPKEY,ASSETTYPE,DESCR,SERVSTAT,OWN,PIPEMATL,PIPELEN,NOMDIAM,INTDIAM,OUTDIAM,DPTH,UPNODE,DWNNODE,CLASS,INSTDATE,JTTYPE,MANUFCT,INSTMTHD,LINEMATL,LINEMTHD,LINEDATE,ASBUILT,SCHEME,DATA_SRC,COMMENTS,ADDDBY,ADDDTTM,MODBY,MODDTTM,CONFIDENCE,CRITICALITY,GlobalID,created_user,created_date,last_edited_user,last_edited_date,Shape__Length","Water Supply Meter","OBJECTID,COMPKEY,ASSETTYPE,DESCR,SERVSTAT,OWN,ZCOORD,INVERTELEV,METERSZ,SERNO,MODELNO,MANUFCT,INSTDATE,ASBUILT,SCHEME,DATA_SRC,COMMENTS,ADDDBY,ADDDTTM,MODBY,MODDTTM,CONFIDENCE,CRITICALITY,GlobalID,created_user,created_date,last_edited_user,last_edited_date","Water Supply Miscellaneous","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,GlobalID,created_user,created_date,last_edited_user,last_edited_date,Shape__Area,Shape__Length","Water Supply Node","OBJECTID,COMPKEY,ASSETTYPE,DESCR,SERVSTAT,OWN,ZCOORD,INVERTELEV,INSTDATE,ASBUILT,SCHEME,DATA_SRC,COMMENTS,ADDDBY,ADDDTTM,MODBY,MODDTTM,CONFIDENCE,CRITICALITY,GlobalID,created_user,created_date,last_edited_user,last_edited_date","Water Supply Pressure Zones","OBJECTID,Id,Zone_Name,Name_Code,Rated_Cons,GlobalID,created_user,created_date,last_edited_user,last_edited_date,Shape__Area,Shape__Length","Water Supply Pumpstation","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,created_user,created_date,last_edited_user,last_edited_date,GlobalID,Shape__Area,Shape__Length","Water Supply Reservoir","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,created_user,created_date,last_edited_user,last_edited_date,GlobalID,Shape__Area,Shape__Length","Water Supply Treatment Plant","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,created_user,created_date,last_edited_user,last_edited_date,GlobalID,Shape__Area,Shape__Length","Water Supply Valve","OBJECTID,COMPKEY,ASSETTYPE,DESCR,SERVSTAT,OWN,ZCOORD,INVERTELEV,VALVESTAT,VALVESZ,SERNO,MODELNO,MANUFCT,INSTDATE,ASBUILT,SCHEME,DATA_SRC,COMMENTS,ADDDBY,ADDDTTM,MODBY,MODDTTM,CONFIDENCE,CRITICALITY,GlobalID,created_user,created_date,last_edited_user,last_edited_date"
    ATTR_ACCUM_MODE = Merge Initiator and Result
    ATTR_CONFLICT_RES = Use Result
    ATTR_IGNORE_NULLS = No
    COMBINE_GEOM = Use Result
    FEATURETYPES = Water Supply Pressure Zones
    FORMAT = ARCGISONLINEFEATURES
    INTERACT = NONE
    ORDER_RESULTS = No
    OUTPUT_FEATURES_DISPLAY = Schema and Data Features
    Water Supply Pressure Zones -> Junction_13
    INITIATOR -> FeatureReader_3 [INITIATOR]
FeatureReader_3
    ARCGISONLINEFEATURES_CREATE_FEATURE_TABLES_FROM_DATA = Yes
    ARCGISONLINEFEATURES_FEATURESERVICE = Queenstown Lakes District Council Open Data/Three Waters Schemes(c2b563e7c41f44a6ad5d04efd337d118)
    ARCGISONLINEFEATURES_FEATURES_PER_REQUEST = 1000
    ARCGISONLINEFEATURES_FORMAT_GUID = YES
    ARCGISONLINEFEATURES_NC = hywell Esri ArcGIS Online
    ARCGISONLINEFEATURES_QUERY_FEATURE_TYPES_FOR_MERGE_FILTERS = Yes
    ARCGISONLINEFEATURES_RESOLVE_DOMAINS = No
    ARCGISONLINEFEATURES_USE_SEARCH_ENVELOPE = NO
    ATTRIBUTES = "Scheme Boundaries","OBJECTID,WaterType,Name,Ownership,Delivery,Maintenance,DecisionDate,VolumeRestrictions,Notes,GlobalID,created_user,created_date,last_edited_user,last_edited_date,Shape__Area,Shape__Length"
    ATTR_ACCUM_MODE = Merge Initiator and Result
    ATTR_CONFLICT_RES = Use Result
    ATTR_IGNORE_NULLS = No
    COMBINE_GEOM = Use Result
    FEATURETYPES = Scheme Boundaries
    FORMAT = ARCGISONLINEFEATURES
    INTERACT = NONE
    ORDER_RESULTS = No
    OUTPUT_FEATURES_DISPLAY = Schema and Data Features
    Scheme Boundaries -> Junction_25
Junction_25
    -> Junction_26
Junction_13
    -> Junction_14
FeatureReader
    ARCGISONLINEFEATURES_CREATE_FEATURE_TABLES_FROM_DATA = Yes
    ARCGISONLINEFEATURES_FEATURESERVICE = Queenstown Lakes District Council Open Data/Three Waters Assets(a99d1860d32f44fbb025142a364d0458)
    ARCGISONLINEFEATURES_FEATURES_PER_REQUEST = 1000
    ARCGISONLINEFEATURES_FORMAT_GUID = YES
    ARCGISONLINEFEATURES_NC = hywell Esri ArcGIS Online
    ARCGISONLINEFEATURES_QUERY_FEATURE_TYPES_FOR_MERGE_FILTERS = Yes
    ARCGISONLINEFEATURES_RESOLVE_DOMAINS = No
    ARCGISONLINEFEATURES_USE_SEARCH_ENVELOPE = NO
    ATTRIBUTES = "Stormwater Channel","OBJECTID,COMPKEY,ASSETTYPE,DESCR,SERVSTAT,OWN,CONMATL,LENGTH,TPWIDTH,BSWIDTH,CHDEPTH,CHANSHAPE,UPNODE,UPSELEV,DWNNODE,DWNELEV,INSTDATE,ASBUILT,SCHEME,DATA_SRC,COMMENTS,ADDDBY,ADDDTTM,MODBY,MODDTTM,CONFIDENCE,CRITICALITY,GlobalID,created_user,created_date,last_edited_user,last_edited_date,Shape__Length","Stormwater Inlet","OBJECTID,COMPKEY,ASSETTYPE,DESCR,SERVSTAT,OWN,ZCOORD,INVERTELEV,CVRTYPE,MANUFCT,INSTDATE,ASBUILT,SCHEME,DATA_SRC,COMMENTS,ADDDBY,ADDDTTM,MODBY,MODDTTM,CONFIDENCE,CRITICALITY,GlobalID,created_user,created_date,last_edited_user,last_edited_date","Stormwater Lateral","OBJECTID,COMPKEY,ASSETTYPE,SRVTYPE,DESCR,SERVSTAT,OWN,PIPEMATL,PIPELEN,NOMDIAM,INTDIAM,OUTDIAM,UPNODE,UPSELEV,DWNNODE,DWNELEV,CLASS,JTTYPE,MANUFCT,INSTDATE,ASBUILT,SCHEME,DATA_SRC,COMMENTS,ADDDBY,ADDDTTM,MODBY,MODDTTM,CONFIDENCE,CRITICALITY,GlobalID,created_user,created_date,last_edited_user,last_edited_date,Shape__Length","Stormwater Main","OBJECTID,COMPKEY,ASSETTYPE,DESCR,SERVSTAT,OWN,PIPEMATL,PIPELEN,NOMDIAM,INTDIAM,OUTDIAM,UPNODE,UPSELEV,DWNNODE,DWNELEV,CLASS,JTTYPE,MANUFCT,INSTMTHD,INSTDATE,LINEMATL,LINEDATE,LINEMTHD,ASBUILT,SCHEME,DATA_SRC,COMMENTS,ADDDBY,ADDDTTM,MODBY,MODDTTM,CONFIDENCE,CRITICALITY,GlobalID,created_user,created_date,last_edited_user,last_edited_date,Shape__Length","Stormwater Manhole","OBJECTID,COMPKEY,ASSETTYPE,DESCR,SERVSTAT,OWN,ZCOORD,INVERTELEV,BARLSHAPE,BARLDIAM,BARLDIM2,CHAMATL,CVRDIAM,CVRTYPE,MANUFCT,INSTDATE,ASBUILT,SCHEME,DATA_SRC,COMMENTS,ADDDBY,ADDDTTM,MODBY,MODDTTM,CONFIDENCE,CRITICALITY,GlobalID,created_user,created_date,last_edited_user,last_edited_date","Stormwater Meter","OBJECTID,COMPKEY,ASSETTYPE,DESCR,SERVSTAT,OWN,ZCOORD,INVERTELEV,METERSZ,SERNO,MODELNO,INSTDATE,ASBUILT,SCHEME,DATA_SRC,COMMENTS,ADDDBY,ADDDTTM,MODBY,MODDTTM,CONFIDENCE,CRITICALITY,GlobalID,created_user,created_date,last_edited_user,last_edited_date","Stormwater Node","OBJECTID,COMPKEY,ASSETTYPE,DESCR,SERVSTAT,OWN,ZCOORD,INVERTELEV,INSTDATE,ASBUILT,SCHEME,DATA_SRC,COMMENTS,ADDDBY,ADDDTTM,MODBY,MODDTTM,CONFIDENCE,CRITICALITY,GlobalID,created_user,created_date,last_edited_user,last_edited_date","Stormwater Pumpstation","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,GlobalID,created_user,created_date,last_edited_user,last_edited_date,Shape__Area,Shape__Length","Stormwater Structure","OBJECTID,COMPKEY,ASSETTYPE,DESCR,SERVSTAT,OWN,ZCOORD,MANUFCT,INSTDATE,ASBUILT,SCHEME,DATA_SRC,COMMENTS,ADDDBY,ADDDTTM,MODBY,MODDTTM,CONFIDENCE,CRITICALITY,GlobalID,created_user,created_date,last_edited_user,last_edited_date","Stormwater Treatment Device","OBJECTID,COMPKEY,ASSETTYPE,DESCR,SERVSTAT,OWN,ZCOORD,INVERTELEV,DEVCAREA,BARLDIAM,BARLDIM2,DVCMATL,CVRDIAM,CVRTYPE,MANUFCT,INSTDATE,ASBUILT,SCHEME,DATA_SRC,COMMENTS,ADDDBY,ADDDTTM,MODBY,MODDTTM,CONFIDENCE,CRITICALITY,GlobalID,created_user,created_date,last_edited_user,last_edited_date,VOIDMAT","Stormwater Treatment Device Area","OBJECTID,COMPKEYREF,COMMENTS,ADDDBY,ADDDTTM,MODBY,MODDTTM,GlobalID,created_user,created_date,last_edited_user,last_edited_date,Shape__Area,Shape__Length","Stormwater Valve","OBJECTID,COMPKEY,ASSETTYPE,DESCR,SERVSTAT,OWN,ZCOORD,INVERTELEV,VALVESTAT,VALVESZ,SERNO,MODELNO,MANUFCT,INSTDATE,ASBUILT,SCHEME,DATA_SRC,COMMENTS,ADDDBY,ADDDTTM,MODBY,MODDTTM,CONFIDENCE,CRITICALITY,GlobalID,created_user,created_date,last_edited_user,last_edited_date","Wastewater Lateral","OBJECTID,COMPKEY,ASSETTYPE,SRVTYPE,DESCR,SERVSTAT,OWN,PIPEMATL,PIPELEN,NOMDIAM,INTDIAM,OUTDIAM,CLASS,MANUFCT,INSTDATE,ASBUILT,SCHEME,DATA_SRC,COMMENTS,ADDDBY,ADDDTTM,MODBY,MODDTTM,CONFIDENCE,CRITICALITY,GlobalID,created_user,created_date,last_edited_user,last_edited_date,Shape__Length","Wastewater Main","OBJECTID,COMPKEY,ASSETTYPE,DESCR,SERVSTAT,OWN,PIPEMATL,PIPELEN,NOMDIAM,INTDIAM,OUTDIAM,UPNODE,UPSELEV,DWNNODE,DWNELEV,CLASS,INSTDATE,JTTYPE,MANUFCT,INSTMTHD,LINEMATL,LINEMTHD,LINEDATE,ASBUILT,SCHEME,DATA_SRC,COMMENTS,ADDDBY,ADDDTTM,MODBY,MODDTTM,CONFIDENCE,CRITICALITY,GlobalID,created_user,created_date,last_edited_user,last_edited_date,Shape__Length","Wastewater Manhole","OBJECTID,COMPKEY,ASSETTYPE,SUBTYPE,DESCR,SERVSTAT,OWN,ZCOORD,INVERTELEV,BARLSHAPE,BARLDIAM,BARLDIM2,CHAMATL,CVRTYPE,CVRDIAM,MANUFCT,INSTDATE,ASBUILT,SCHEME,DATA_SRC,COMMENTS,ADDDBY,ADDDTTM,MODBY,MODDTTM,CONFIDENCE,CRITICALITY,GlobalID,created_user,created_date,last_edited_user,last_edited_date","Wastewater Meter","OBJECTID,COMPKEY,ASSETTYPE,DESCR,SERVSTAT,OWN,ZCOORD,INVERTELEV,METERSZ,SERNO,MODELNO,MANUFCT,INSTDATE,ASBUILT,SCHEME,DATA_SRC,COMMENTS,ADDDBY,ADDDTTM,MODBY,MODDTTM,CONFIDENCE,CRITICALITY,GlobalID,created_user,created_date,last_edited_user,last_edited_date","Wastewater Node","OBJECTID,COMPKEY,ASSETTYPE,DESCR,SERVSTAT,OWN,ZCOORD,INVERTELEV,INSTDATE,ASBUILT,SCHEME,DATA_SRC,COMMENTS,ADDDBY,ADDDTTM,MODBY,MODDTTM,CONFIDENCE,CRITICALITY,GlobalID,created_user,created_date,last_edited_user,last_edited_date","Wastewater Pumpstation","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,created_user,created_date,last_edited_user,last_edited_date,GlobalID,Shape__Area,Shape__Length","Wastewater Treatment Plant","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,created_user,created_date,last_edited_user,last_edited_date,GlobalID,Shape__Area,Shape__Length","Wastewater Valve","OBJECTID,COMPKEY,ASSETTYPE,DESCR,SERVSTAT,OWN,ZCOORD,INVERTELEV,VALVESTAT,VALVESZ,SERNO,MODELNO,MANUFCT,INSTDATE,ASBUILT,SCHEME,DATA_SRC,COMMENTS,ADDDBY,ADDDTTM,MODBY,MODDTTM,CONFIDENCE,CRITICALITY,GlobalID,created_user,created_date,last_edited_user,last_edited_date","Water Supply Backflow","OBJECTID,COMPKEY,ASSETTYPE,DESCR,SERVSTAT,OWN,ZCOORD,INVERTELEV,VALVESTAT,VALVESZ,SERNO,MODELNO,MANUFCT,INSTDATE,ASBUILT,SCHEME,DATA_SRC,COMMENTS,ADDDBY,ADDDTTM,MODBY,MODDTTM,CONFIDENCE,CRITICALITY,GlobalID,created_user,created_date,last_edited_user,last_edited_date","Water Supply Hydrant","OBJECTID,COMPKEY,ASSETTYPE,DESCR,SERVSTAT,OWN,ZCOORD,INVERTELEV,MODELNO,MANUFCT,INSTDATE,ASBUILT,SCHEME,DATA_SRC,COMMENTS,ADDDBY,ADDDTTM,MODBY,MODDTTM,CONFIDENCE,CRITICALITY,GlobalID,created_user,created_date,last_edited_user,last_edited_date","Water Supply Lateral","OBJECTID,COMPKEY,ASSETTYPE,SRVTYPE,DESCR,SERVSTAT,OWN,PIPEMATL,PIPELEN,NOMDIAM,INTDIAM,OUTDIAM,CLASS,MANUFCT,INSTDATE,ASBUILT,SCHEME,DATA_SRC,COMMENTS,ADDDBY,ADDDTTM,MODBY,MODDTTM,CONFIDENCE,CRITICALITY,GlobalID,created_user,created_date,last_edited_user,last_edited_date,Shape__Length","Water Supply Main","OBJECTID,COMPKEY,ASSETTYPE,DESCR,SERVSTAT,OWN,PIPEMATL,PIPELEN,NOMDIAM,INTDIAM,OUTDIAM,DPTH,UPNODE,DWNNODE,CLASS,INSTDATE,JTTYPE,MANUFCT,INSTMTHD,LINEMATL,LINEMTHD,LINEDATE,ASBUILT,SCHEME,DATA_SRC,COMMENTS,ADDDBY,ADDDTTM,MODBY,MODDTTM,CONFIDENCE,CRITICALITY,GlobalID,created_user,created_date,last_edited_user,last_edited_date,Shape__Length","Water Supply Meter","OBJECTID,COMPKEY,ASSETTYPE,DESCR,SERVSTAT,OWN,ZCOORD,INVERTELEV,METERSZ,SERNO,MODELNO,MANUFCT,INSTDATE,ASBUILT,SCHEME,DATA_SRC,COMMENTS,ADDDBY,ADDDTTM,MODBY,MODDTTM,CONFIDENCE,CRITICALITY,GlobalID,created_user,created_date,last_edited_user,last_edited_date","Water Supply Miscellaneous","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,GlobalID,created_user,created_date,last_edited_user,last_edited_date,Shape__Area,Shape__Length","Water Supply Node","OBJECTID,COMPKEY,ASSETTYPE,DESCR,SERVSTAT,OWN,ZCOORD,INVERTELEV,INSTDATE,ASBUILT,SCHEME,DATA_SRC,COMMENTS,ADDDBY,ADDDTTM,MODBY,MODDTTM,CONFIDENCE,CRITICALITY,GlobalID,created_user,created_date,last_edited_user,last_edited_date","Water Supply Pressure Zones","OBJECTID,Id,Zone_Name,Name_Code,Rated_Cons,GlobalID,created_user,created_date,last_edited_user,last_edited_date,Shape__Area,Shape__Length","Water Supply Pumpstation","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,created_user,created_date,last_edited_user,last_edited_date,GlobalID,Shape__Area,Shape__Length","Water Supply Reservoir","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,created_user,created_date,last_edited_user,last_edited_date,GlobalID,Shape__Area,Shape__Length","Water Supply Treatment Plant","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,created_user,created_date,last_edited_user,last_edited_date,GlobalID,Shape__Area,Shape__Length","Water Supply Valve","OBJECTID,COMPKEY,ASSETTYPE,DESCR,SERVSTAT,OWN,ZCOORD,INVERTELEV,VALVESTAT,VALVESZ,SERNO,MODELNO,MANUFCT,INSTDATE,ASBUILT,SCHEME,DATA_SRC,COMMENTS,ADDDBY,ADDDTTM,MODBY,MODDTTM,CONFIDENCE,CRITICALITY,GlobalID,created_user,created_date,last_edited_user,last_edited_date"
    ATTR_ACCUM_MODE = Merge Initiator and Result
    ATTR_CONFLICT_RES = Use Result
    ATTR_IGNORE_NULLS = No
    COMBINE_GEOM = Use Result
    FEATURETYPES = Water Supply Backflow Water Supply Hydrant Water Supply Lateral Water Supply Main Water Supply Meter Water Supply Miscellaneous Water Supply Node Water Supply Pumpstation Water Supply Reservoir Water Supply Treatment Plant Water Supply Valve
    FORMAT = ARCGISONLINEFEATURES
    INTERACT = NONE
    ORDER_RESULTS = No
    OUTPUT_FEATURES_DISPLAY = Schema and Data Features
    Water Supply Backflow -> Junction
    Water Supply Hydrant -> Junction_5
    Water Supply Lateral -> Junction_11
    Water Supply Main -> Junction_11
    Water Supply Meter -> Junction_7
    Water Supply Miscellaneous -> Junction_21
    Water Supply Node -> Junction_9
    Water Supply Pumpstation -> Junction_17
    Water Supply Reservoir -> Junction_19
    Water Supply Treatment Plant -> Junction_15
    Water Supply Valve -> Junction_3
    <REJECTED> -> FeatureReader__Rejected_
Junction
    -> Junction_2
Junction_5
    -> Junction_6
Junction_11
    -> Junction_12
Junction_7
    -> Junction_8
Junction_21
    -> Junction_22
Junction_9
    -> Junction_10
Junction_17
    -> Junction_18
Junction_19
    -> Junction_20
Junction_15
    -> Junction_16
Junction_3
    -> Junction_4
FeatureReader__Rejected_: Logger
    LOG_FEATURE = LOG_ONLY
    MAXCOORDS = 20
    MAXFEATS = 20
    MESSAGE = Feature is:
    SEVERITY = INFO

Bookmark: transform: dirty polygons2shp
Junction_26
    -> Tester
Note: Tester [Tester] / Test Clauses: Left ValueOperatorRight Value@Value(WaterType)=$(water_type)Advanced: / Preserve Feature Order: Per Output Port
Tester
    BOOL_OP = OR
    TEST_CLAUSE = TEST @Value(WaterType) = $(water_type)
    TEST_MODE = TEST
    PASSED -> _simple_geom [Deaggregator_Input]
_simple_geom
    TOLERANCE = 1
    Generalizer_Output -> AttributeManager
AttributeManager
    ATTR_TABLE:
      REMOVE _creation_instance (uint64)
      REMOVE Ownership (varchar(255))
      REMOVE Delivery (varchar(255))
      REMOVE Maintenance (varchar(255))
      REMOVE DecisionDate (datetime)
      REMOVE VolumeRestrictions (int32)
      REMOVE GlobalID (varchar(38))
      REMOVE created_user (varchar(255))
      REMOVE created_date (datetime)
      REMOVE last_edited_user (varchar(255))
      REMOVE last_edited_date (datetime)
      REMOVE Shape__Area (real64)
      REMOVE Shape__Length (real64)
      REMOVE _part_number (uint64)
      REMOVE _geometry_name (buffer)
    -> FeatureWriter_9 [Output]
FeatureWriter_9
    DATASET = $(dir)
    DATASET_ATTR = _dataset
    FEATURE_TYPE_LIST_ATTR = _feature_types
    FORMAT = SHAPEFILE
    SHAPEFILE_COMPRESSED_FILE = No
    SHAPEFILE_DATASET_SPLITTING = Yes
    SHAPEFILE_DATETIME_STORAGE = TIMESTAMP_STRING
    SHAPEFILE_DESTINATION_DATASETTYPE_VALIDATION = Yes
    SHAPEFILE_DIMENSION = AUTO
    SHAPEFILE_ENCODING = utf-8
    SHAPEFILE_ENFORCE_ATTRIBUTE_LIMIT = No
    SHAPEFILE_MEASURES_AS_Z = No
    SHAPEFILE_PERMIT_NONASCII_FIRST_ATTRNAME = Yes
    SHAPEFILE_REQUIRE_FIRST_ATTRNAME_ALPHA = Yes
    SHAPEFILE_SPATIAL_INDEXES = NONE
    SHAPEFILE_SURFACE_SOLID_STORAGE = PATCH
    TOTAL_FEATURES_WRITTEN_ATTR = _total_features_written
Junction_14
    -> Deaggregator_6
Deaggregator_6
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> AttributeCreator
AttributeCreator
    ATTR_TABLE = SET_TO id2 (varchar(200)) = FME_CONDITIONAL:DEFAULT_VALUE'@Value(OBJECTID)'BOOL_OP;OR;COMPOSITE_TEST;1;TEST _part_number ATTRIBUTE_HAS_A_VALUE _FME_BLANK_STRING_'@Value(OBJECTID)_@Value(_part_number)'FME_NUM_CONDITIONS2___
    -> DateTimeConverter_7
DateTimeConverter_7
    DATETIME_ATTR = created_date last_edited_date
    OUT_FORMAT = %Y%m%d%H%M%S
    PASSTHROUGH = NO
    REPAIR_INPUT = YES
    -> FeatureWriter_11 [Output]
    <REJECTED> -> FeatureWriter_11 [Output]
FeatureWriter_11
    DATASET = $(dir)
    DATASET_ATTR = _dataset
    FEATURE_TYPE_LIST_ATTR = _feature_types
    FORMAT = SHAPEFILE
    SHAPEFILE_COMPRESSED_FILE = No
    SHAPEFILE_DATASET_SPLITTING = Yes
    SHAPEFILE_DATETIME_STORAGE = TIMESTAMP_STRING
    SHAPEFILE_DESTINATION_DATASETTYPE_VALIDATION = Yes
    SHAPEFILE_DIMENSION = AUTO
    SHAPEFILE_ENCODING = utf-8
    SHAPEFILE_ENFORCE_ATTRIBUTE_LIMIT = No
    SHAPEFILE_MEASURES_AS_Z = No
    SHAPEFILE_PERMIT_NONASCII_FIRST_ATTRNAME = Yes
    SHAPEFILE_REQUIRE_FIRST_ATTRNAME_ALPHA = Yes
    SHAPEFILE_SPATIAL_INDEXES = NONE
    SHAPEFILE_SURFACE_SOLID_STORAGE = PATCH
    TOTAL_FEATURES_WRITTEN_ATTR = _total_features_written

Bookmark: transform: nodes2csv
Junction_2
    -> _nodes [CoordinateExtractor_Input]
Junction_6
    -> _nodes_2 [CoordinateExtractor_Input]
_nodes_2
    GeometryRemover_Output -> DateTimeConverter_3
DateTimeConverter_3
    DATETIME_ATTR = ADDDTTM INSTDATE created_date MODDTTM last_edited_date
    OUT_FORMAT = %Y%m%d%H%M%S
    PASSTHROUGH = NO
    REPAIR_INPUT = YES
    -> FeatureWriter_2 [_Rejected_00]
    <REJECTED> -> FeatureWriter_2 [_Rejected_00]
FeatureWriter_2
    CSV2_COORDINATE_SYSTEM_GRANULARITY = FEATURE_TYPE
    CSV2_DELIMITER = ,
    CSV2_ENCODING = UTF-8
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = if_needed
    CSV2_QUALIFY_FIELD_VALUES = if_needed
    CSV2_ROW_TERMINATION = System
    CSV2_TREAT_EMBEDDED_FIELD_QUALIFIERS_AS_UNSAFE = Yes
    CSV2_WRITE_BOM_FOR_UNICODE = Yes
    CSV2_WRITE_FIELD_NAMES = firstrow
    CSV2_WRITE_SCHEMA_FILE = NO
    DATASET = $(dir)
    DATASET_ATTR = _dataset
    FEATURE_TYPE_LIST_ATTR = _feature_types
    FORMAT = CSV2
    TOTAL_FEATURES_WRITTEN_ATTR = _total_features_written
Junction_8
    -> _nodes_3 [CoordinateExtractor_Input]
_nodes_3
    GeometryRemover_Output -> DateTimeConverter_4
DateTimeConverter_4
    DATETIME_ATTR = ADDDTTM INSTDATE created_date MODDTTM last_edited_date
    OUT_FORMAT = %Y%m%d%H%M%S
    PASSTHROUGH = NO
    REPAIR_INPUT = YES
    -> FeatureWriter_3 [_Rejected_01]
    <REJECTED> -> FeatureWriter_3 [_Rejected_01]
FeatureWriter_3
    CSV2_COORDINATE_SYSTEM_GRANULARITY = FEATURE_TYPE
    CSV2_DELIMITER = ,
    CSV2_ENCODING = UTF-8
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = if_needed
    CSV2_QUALIFY_FIELD_VALUES = if_needed
    CSV2_ROW_TERMINATION = System
    CSV2_TREAT_EMBEDDED_FIELD_QUALIFIERS_AS_UNSAFE = Yes
    CSV2_WRITE_BOM_FOR_UNICODE = Yes
    CSV2_WRITE_FIELD_NAMES = firstrow
    CSV2_WRITE_SCHEMA_FILE = NO
    DATASET = $(dir)
    DATASET_ATTR = _dataset
    FEATURE_TYPE_LIST_ATTR = _feature_types
    FORMAT = CSV2
    TOTAL_FEATURES_WRITTEN_ATTR = _total_features_written
Junction_10
    -> _nodes_4 [CoordinateExtractor_Input]
_nodes_4
    GeometryRemover_Output -> DateTimeConverter_5
DateTimeConverter_5
    DATETIME_ATTR = ADDDTTM INSTDATE created_date MODDTTM last_edited_date
    OUT_FORMAT = %Y%m%d%H%M%S
    PASSTHROUGH = NO
    REPAIR_INPUT = YES
    -> FeatureWriter_4 [_Rejected_02]
    <REJECTED> -> FeatureWriter_4 [_Rejected_02]
FeatureWriter_4
    CSV2_COORDINATE_SYSTEM_GRANULARITY = FEATURE_TYPE
    CSV2_DELIMITER = ,
    CSV2_ENCODING = UTF-8
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = if_needed
    CSV2_QUALIFY_FIELD_VALUES = if_needed
    CSV2_ROW_TERMINATION = System
    CSV2_TREAT_EMBEDDED_FIELD_QUALIFIERS_AS_UNSAFE = Yes
    CSV2_WRITE_BOM_FOR_UNICODE = Yes
    CSV2_WRITE_FIELD_NAMES = firstrow
    CSV2_WRITE_SCHEMA_FILE = NO
    DATASET = $(dir)
    DATASET_ATTR = _dataset
    FEATURE_TYPE_LIST_ATTR = _feature_types
    FORMAT = CSV2
    TOTAL_FEATURES_WRITTEN_ATTR = _total_features_written
Junction_4
    -> _nodes [CoordinateExtractor_Input]
_nodes
    GeometryRemover_Output -> DateTimeConverter_2
DateTimeConverter_2
    DATETIME_ATTR = ADDDTTM INSTDATE created_date MODDTTM last_edited_date
    OUT_FORMAT = %Y%m%d%H%M%S
    PASSTHROUGH = NO
    REPAIR_INPUT = YES
    -> FeatureWriter [_Rejected_]
    <REJECTED> -> FeatureWriter [_Rejected_]
FeatureWriter
    CSV2_COORDINATE_SYSTEM_GRANULARITY = FEATURE_TYPE
    CSV2_DELIMITER = ,
    CSV2_ENCODING = UTF-8
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = if_needed
    CSV2_QUALIFY_FIELD_VALUES = if_needed
    CSV2_ROW_TERMINATION = System
    CSV2_TREAT_EMBEDDED_FIELD_QUALIFIERS_AS_UNSAFE = Yes
    CSV2_WRITE_BOM_FOR_UNICODE = Yes
    CSV2_WRITE_FIELD_NAMES = firstrow
    CSV2_WRITE_SCHEMA_FILE = NO
    DATASET = $(dir)
    DATASET_ATTR = _dataset
    FEATURE_TYPE_LIST_ATTR = _feature_types
    FORMAT = CSV2
    TOTAL_FEATURES_WRITTEN_ATTR = _total_features_written

Bookmark: transform: polylines2csv
Junction_12
    -> _startend [CoordinateExtractor_Input_1]
_startend
    AttributeCreator_Output -> _linestring [ArcStroker_Input]
_linestring
    GeometryRemover_Output_1 -> DateTimeConverter_6
DateTimeConverter_6
    DATETIME_ATTR = ADDDTTM INSTDATE created_date MODDTTM last_edited_date
    OUT_FORMAT = %Y%m%d%H%M%S
    PASSTHROUGH = NO
    REPAIR_INPUT = YES
    -> FeatureWriter_5 [GeometryRemover_Output_1]
    <REJECTED> -> FeatureWriter_5 [GeometryRemover_Output_1]
FeatureWriter_5
    CSV2_COORDINATE_SYSTEM_GRANULARITY = FEATURE_TYPE
    CSV2_DELIMITER = ,
    CSV2_ENCODING = UTF-8
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = if_needed
    CSV2_QUALIFY_FIELD_VALUES = if_needed
    CSV2_ROW_TERMINATION = System
    CSV2_TREAT_EMBEDDED_FIELD_QUALIFIERS_AS_UNSAFE = Yes
    CSV2_WRITE_BOM_FOR_UNICODE = Yes
    CSV2_WRITE_FIELD_NAMES = firstrow
    CSV2_WRITE_SCHEMA_FILE = NO
    DATASET = $(dir)
    DATASET_ATTR = _dataset
    FEATURE_TYPE_LIST_ATTR = _feature_types
    FORMAT = CSV2
    TOTAL_FEATURES_WRITTEN_ATTR = _total_features_written

Bookmark: transform: polygons2csv
Junction_22
    -> GeometryFilter
GeometryFilter
    FILTER_MODE = SIMPLE
    FILTER_MULTI = FILTER_TYPES]Area]FME_CONTROLLER_QUERY_FILE]]FME_CONTROLLER_CHOICE]Simple
    Area -> Deaggregator_5
Deaggregator_5
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> AttributeCreator_5
AttributeCreator_5
    ATTR_TABLE = SET_TO id (varchar(200)) = FME_CONDITIONAL:DEFAULT_VALUE'@Value(COMPKEY)'BOOL_OP;OR;COMPOSITE_TEST;1;TEST _part_number ATTRIBUTE_HAS_A_VALUE _FME_BLANK_STRING_'@Value(COMPKEY)_@Value(_part_number)'FME_NUM_CONDITIONS2___
    -> _polygons_5 [GeometryExtractor_Input_1]
_polygons_5: _polygons_2
    GeometryRemover_Output_2 -> DateTimeConverter_11
DateTimeConverter_11
    DATETIME_ATTR = ADDDTTM INSTDATE created_date MODDTTM last_edited_date
    OUT_FORMAT = %Y%m%d%H%M%S
    PASSTHROUGH = NO
    REPAIR_INPUT = YES
    -> FeatureWriter_10 [Output]
    <REJECTED> -> FeatureWriter_10 [Output]
FeatureWriter_10
    CSV2_COORDINATE_SYSTEM_GRANULARITY = FEATURE_TYPE
    CSV2_DELIMITER = ,
    CSV2_ENCODING = UTF-8
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = if_needed
    CSV2_QUALIFY_FIELD_VALUES = if_needed
    CSV2_ROW_TERMINATION = System
    CSV2_TREAT_EMBEDDED_FIELD_QUALIFIERS_AS_UNSAFE = Yes
    CSV2_WRITE_BOM_FOR_UNICODE = Yes
    CSV2_WRITE_FIELD_NAMES = firstrow
    CSV2_WRITE_SCHEMA_FILE = NO
    DATASET = $(dir)
    DATASET_ATTR = _dataset
    FEATURE_TYPE_LIST_ATTR = _feature_types
    FORMAT = CSV2
    TOTAL_FEATURES_WRITTEN_ATTR = _total_features_written
Junction_18
    -> Deaggregator_2
Deaggregator_2
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> AttributeCreator_2
AttributeCreator_2
    ATTR_TABLE = SET_TO id (varchar(200)) = FME_CONDITIONAL:DEFAULT_VALUE'@Value(COMPKEY)'BOOL_OP;OR;COMPOSITE_TEST;1;TEST _part_number ATTRIBUTE_HAS_A_VALUE _FME_BLANK_STRING_'@Value(COMPKEY)_@Value(_part_number)'FME_NUM_CONDITIONS2___
    -> _polygons_2 [GeometryExtractor_Input_1]
_polygons_2
    GeometryRemover_Output_2 -> DateTimeConverter_8
DateTimeConverter_8
    DATETIME_ATTR = ADDDTTM INSTDATE created_date MODDTTM last_edited_date
    OUT_FORMAT = %Y%m%d%H%M%S
    PASSTHROUGH = NO
    REPAIR_INPUT = YES
    -> FeatureWriter_6 [GeometryRemover_Output_2]
    <REJECTED> -> FeatureWriter_6 [GeometryRemover_Output_2]
FeatureWriter_6
    CSV2_COORDINATE_SYSTEM_GRANULARITY = FEATURE_TYPE
    CSV2_DELIMITER = ,
    CSV2_ENCODING = UTF-8
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = if_needed
    CSV2_QUALIFY_FIELD_VALUES = if_needed
    CSV2_ROW_TERMINATION = System
    CSV2_TREAT_EMBEDDED_FIELD_QUALIFIERS_AS_UNSAFE = Yes
    CSV2_WRITE_BOM_FOR_UNICODE = Yes
    CSV2_WRITE_FIELD_NAMES = firstrow
    CSV2_WRITE_SCHEMA_FILE = NO
    DATASET = $(dir)
    DATASET_ATTR = _dataset
    FEATURE_TYPE_LIST_ATTR = _feature_types
    FORMAT = CSV2
    TOTAL_FEATURES_WRITTEN_ATTR = _total_features_written
Junction_16
    -> Deaggregator_4
Deaggregator_4
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> AttributeCreator_4
AttributeCreator_4
    ATTR_TABLE = SET_TO id (varchar(200)) = FME_CONDITIONAL:DEFAULT_VALUE'@Value(COMPKEY)'BOOL_OP;OR;COMPOSITE_TEST;1;TEST _part_number ATTRIBUTE_HAS_A_VALUE _FME_BLANK_STRING_'@Value(COMPKEY)_@Value(_part_number)'FME_NUM_CONDITIONS2___
    -> _polygons_4 [GeometryExtractor_Input_1]
_polygons_4: _polygons_2
    GeometryRemover_Output_2 -> DateTimeConverter_10
DateTimeConverter_10
    DATETIME_ATTR = ADDDTTM INSTDATE created_date MODDTTM last_edited_date
    OUT_FORMAT = %Y%m%d%H%M%S
    PASSTHROUGH = NO
    REPAIR_INPUT = YES
    -> FeatureWriter_8 [GeometryRemover_Output_201]
    <REJECTED> -> FeatureWriter_8 [GeometryRemover_Output_201]
FeatureWriter_8
    CSV2_COORDINATE_SYSTEM_GRANULARITY = FEATURE_TYPE
    CSV2_DELIMITER = ,
    CSV2_ENCODING = UTF-8
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = if_needed
    CSV2_QUALIFY_FIELD_VALUES = if_needed
    CSV2_ROW_TERMINATION = System
    CSV2_TREAT_EMBEDDED_FIELD_QUALIFIERS_AS_UNSAFE = Yes
    CSV2_WRITE_BOM_FOR_UNICODE = Yes
    CSV2_WRITE_FIELD_NAMES = firstrow
    CSV2_WRITE_SCHEMA_FILE = NO
    DATASET = $(dir)
    DATASET_ATTR = _dataset
    FEATURE_TYPE_LIST_ATTR = _feature_types
    FORMAT = CSV2
    TOTAL_FEATURES_WRITTEN_ATTR = _total_features_written

Bookmark: transform: polygons2points2csv
Junction_20
    -> Deaggregator_3
Deaggregator_3
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> AttributeCreator_3
AttributeCreator_3
    ATTR_TABLE = SET_TO id (varchar(200)) = FME_CONDITIONAL:DEFAULT_VALUE'@Value(COMPKEY)'BOOL_OP;OR;COMPOSITE_TEST;1;TEST _part_number ATTRIBUTE_HAS_A_VALUE _FME_BLANK_STRING_'@Value(COMPKEY)_@Value(_part_number)'FME_NUM_CONDITIONS2___
    -> CenterPointReplacer
CenterPointReplacer
    POINTTYPE = CENTER
    POINT -> CoordinateExtractor
CoordinateExtractor
    LIST_NAME = _indices
    MODE = All Coordinates
    -> AttributeCreator_6
AttributeCreator_6
    ATTR_TABLE:
      SET_TO x (varchar(200)) = @Value(_indices{0}.x)
      SET_TO y (varchar(200)) = @Value(_indices{0}.y)
    -> DateTimeConverter_9
DateTimeConverter_9
    DATETIME_ATTR = ADDDTTM INSTDATE created_date MODDTTM last_edited_date
    OUT_FORMAT = %Y%m%d%H%M%S
    PASSTHROUGH = NO
    REPAIR_INPUT = YES
    -> FeatureWriter_7 [GeometryRemover_Output_200]
    <REJECTED> -> FeatureWriter_7 [GeometryRemover_Output_200]
FeatureWriter_7
    CSV2_COORDINATE_SYSTEM_GRANULARITY = FEATURE_TYPE
    CSV2_DELIMITER = ,
    CSV2_ENCODING = UTF-8
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = if_needed
    CSV2_QUALIFY_FIELD_VALUES = if_needed
    CSV2_ROW_TERMINATION = System
    CSV2_TREAT_EMBEDDED_FIELD_QUALIFIERS_AS_UNSAFE = Yes
    CSV2_WRITE_BOM_FOR_UNICODE = Yes
    CSV2_WRITE_FIELD_NAMES = firstrow
    CSV2_WRITE_SCHEMA_FILE = NO
    DATASET = $(dir)
    DATASET_ATTR = _dataset
    FEATURE_TYPE_LIST_ATTR = _feature_types
    FORMAT = CSV2
    TOTAL_FEATURES_WRITTEN_ATTR = _total_features_written

FME custom transformer _linestring

ArcStroker_Input (input)
    -> ArcStroker
GeometryRemover_Output_1 (output)

Bookmark: New Bookmark
ArcStroker
    MAKE_POLY = No
    NUM = 0
    STROKE_CHOICE = Number of Interpolated Edges
    STROKED -> GeometryExtractor
GeometryExtractor
    ATTR = point_array
    KIND_LONG = OGC Well Known Text
    OGCVERSION = 1.2
    OGC_WKT_PRECISION_DISPLAY = 64-bit
    REMOVE_GEOMETRY = No
    -> StringReplacer
    <REJECTED> -> GeometryExtractor__Rejected_
StringReplacer
    CASE = NO
    FIND_TEXT = LINESTRING (
    NO_MATCH = _FME_NO_OP_
    REGEXP = NO
    REPLACE_TEXT = {
    SRC_ATTRS = point_array
    -> StringReplacer_2
StringReplacer_2
    CASE = NO
    FIND_TEXT = )
    NO_MATCH = _FME_NO_OP_
    REGEXP = NO
    REPLACE_TEXT = }
    SRC_ATTRS = point_array
    -> StringReplacer_3
StringReplacer_3
    CASE = NO
    FIND_TEXT = " "
    NO_MATCH = _FME_NO_OP_
    REGEXP = NO
    REPLACE_TEXT = ,
    SRC_ATTRS = point_array
    -> GeometryRemover
GeometryRemover
    REMOVE_COORDSYS = No
    -> GeometryRemover_Output_1 (output)
GeometryExtractor__Rejected_: Logger
    LOG_FEATURE = LOG_ONLY
    MAXCOORDS = 20
    MAXFEATS = 20
    MESSAGE = Feature is:
    SEVERITY = INFO

FME custom transformer _polygons_2

GeometryExtractor_Input_1 (input)
    -> GeometryExtractor
GeometryRemover_Output_2 (output)

Bookmark: New Bookmark
GeometryExtractor
    ATTR = point_array
    KIND_LONG = OGC Well Known Text
    OGCVERSION = 1.2
    OGC_WKT_PRECISION_DISPLAY = 64-bit
    REMOVE_GEOMETRY = No
    -> StringReplacer
StringReplacer
    CASE = NO
    FIND_TEXT = POLYGON (
    NO_MATCH = _FME_NO_OP_
    REGEXP = NO
    SRC_ATTRS = point_array
    -> StringReplacer_2
StringReplacer_2
    CASE = NO
    FIND_TEXT = (
    NO_MATCH = _FME_NO_OP_
    REGEXP = NO
    REPLACE_TEXT = {
    SRC_ATTRS = point_array
    -> StringReplacer_3
StringReplacer_3
    CASE = NO
    FIND_TEXT = ))
    NO_MATCH = _FME_NO_OP_
    REGEXP = NO
    REPLACE_TEXT = }
    SRC_ATTRS = point_array
    -> StringReplacer_4
StringReplacer_4
    CASE = NO
    FIND_TEXT = " "
    NO_MATCH = _FME_NO_OP_
    REGEXP = NO
    REPLACE_TEXT = ,
    SRC_ATTRS = point_array
    -> GeometryRemover
GeometryRemover
    REMOVE_COORDSYS = No
    -> GeometryRemover_Output_2 (output)

FME custom transformer _simple_geom

Parameters:
- TOLERANCE = 1   # Generalization Tolerance

Deaggregator_Input (input)
    -> Deaggregator
Deaggregator
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> Generalizer
Generalizer
    ALG_TEXT = Douglas (Generalize)
    PRESERVE = No
    PRESERVE_PATHS = No
    TOLERANCE = $(TOLERANCE)
    -> DonutHoleExtractor
DonutHoleExtractor
    DEAGGREGATE_INPUT = No
    OUTERSHELL -> Generalizer_Output (output)
    OUTERSHELL -> AreaGapAndOverlapCleaner
    <REJECTED> -> DonutHoleExtractor__Rejected_
AreaGapAndOverlapCleaner
    CLEANING_TOLERANCE = 5
    CONNECT_Z_MODE = First Wins
    DEAGGREGATE_INPUT = NO
    FILL_ALL_GAPS = No
    MEASURE_TYPE = Continuous
    MISSING_VAL_MODE = Compute
    REPAIR_METHOD = Longest Boundary
    REPAIRED -> SliverOutput (output)
SliverOutput (output)
Generalizer_Output (output)
DonutHoleExtractor__Rejected_: Logger
    LOG_FEATURE = LOG_ONLY
    MAXCOORDS = 20
    MAXFEATS = 20
    MESSAGE = Feature is:
    SEVERITY = INFO

FME custom transformer _startend

CoordinateExtractor_Input_1 (input)
    -> CoordinateExtractor
CoordinateExtractor
    LIST_NAME = _indices
    MODE = All Coordinates
    -> ListElementCounter
    <REJECTED> -> CoordinateExtractor__Rejected_
CoordinateExtractor__Rejected_: Logger
    LOG_FEATURE = LOG_ONLY
    MAXCOORDS = 20
    MAXFEATS = 20
    MESSAGE = Feature is:
    SEVERITY = INFO
ListElementCounter
    CNT_ATTR = _element_count
    LIST_NAME = _indices{}
    -> AttributeCreator
AttributeCreator
    ATTR_TABLE:
      SET_TO x_start (real64) = @Value(_indices{0}.x)
      SET_TO y_start (real64) = @Value(_indices{0}.y)
      SET_TO x_end (real64) = @Value(_indices{@Evaluate(@Value(_element_count)-1)}.x)
      SET_TO y_end (real64) = @Value(_indices{@Evaluate(@Value(_element_count)-1)}.y)
    -> AttributeCreator_Output (output)
AttributeCreator_Output (output)

FME custom transformer _nodes

CoordinateExtractor_Input (input)
    -> CoordinateExtractor
CoordinateExtractor
    LIST_NAME = _indices
    MODE = All Coordinates
    -> AttributeCreator
AttributeCreator
    ATTR_TABLE:
      SET_TO x (varchar(200)) = @Value(_indices{0}.x)
      SET_TO y (varchar(200)) = @Value(_indices{0}.y)
    -> GeometryRemover
GeometryRemover
    REMOVE_COORDSYS = No
    -> GeometryRemover_Output (output)
GeometryRemover_Output (output)
