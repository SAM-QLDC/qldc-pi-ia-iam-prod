FME workspace export network to topojson.fmw

Bookmark: datetime
Creator
    GEOMTYPE = Geometry Object
    NUM = 1
    CREATED -> DateTimeStamper
DateTimeStamper
    DATETIME_ATTR = origin_utc
    INCLUDE_FRAC_SECONDS = NO
    INCLUDE_OFFSET = NO
    STAMP_TYPE = datetime
    TIMEZONE = utc
    -> Junction
    -> Junction_11
    -> Junction_13
Junction_11
    -> Junction_12
Junction
    -> Junction_3
Junction_13
    -> Junction_14

Bookmark: extract: water supply
Junction_12
    -> _watersupply [INITIATOR]
_watersupply: FeatureReader
    ATTRIBUTES = Fitting,"area_code,asset_id,condition_grade,criticality,current_value,date_cleaned,date_installed,date_renewed,diameter,elevation,gps_survey_date,headloss,inspection_cost,install_cost,joint_type,lat_distance,lat_pipe_id,lifetime,location,manhole_id,manufacturer,material,mobile_uid,node_id,operational_status,owner,photo,photo_filename,photo_ref,planning_status,rehab_cost,replace_cost,security,sketch,sketch_filename,sketch_ref,soil_type,surface_type,survey_date,thrust_protection,type,uid,user_date_1,user_date_2,user_date_3,user_date_4,user_date_5,user_number_10,user_number_11,user_number_12,user_number_13,user_number_14,user_number_15,user_number_16,user_number_17,user_number_18,user_number_19,user_number_2,user_number_20,user_number_21,user_number_22,user_number_23,user_number_24,user_number_25,user_number_26,user_number_27,user_number_28,user_number_29,user_number_3,user_number_30,user_number_31,user_number_32,user_number_33,user_number_34,user_number_35,user_number_36,user_number_37,user_number_38,user_number_39,user_number_4,user_number_40,user_number_5,user_number_6,user_number_7,user_number_8,user_number_9,user_text_1,user_text_10,user_text_11,user_text_12,user_text_13,user_text_14,user_text_15,user_text_16,x,y,fme_basename",Hydrant,"area_code,asset_id,available_flow,barrel_diameter,barrel_height,bury_depth,condition_grade,criticality,current_value,date_cleaned,date_installed,date_last_flushed,date_renewed,defects,drain_indicator,elevation,fire_dept_code,fire_zone,gps_survey_date,headloss,inspection_cost,install_cost,lat_distance,lat_pipe_id,lifetime,location,logger_fits_in_chamber,manhole_id,manufacturer,mobile_uid,node_id,nozzle_diameter_1,nozzle_diameter_2,nozzle_diameter_3,nozzle_height,nozzle_outlet_config,nozzle_thread_type,operational_status,owner,photo,photo_filename,photo_ref,planning_status,polywrap_indicator,pressure,pressure_rating,rehab_cost,replace_cost,riser_diameter,riser_length,security,sketch,sketch_filename,sketch_ref,soil_type,surface_type,survey_date,uid,user_date_1,user_date_2,user_date_3,user_date_4,user_date_5,user_number_14,user_number_15,user_number_16,user_number_17,user_number_18,user_number_19,user_number_2,user_number_20,user_number_21,user_number_22,user_number_23,user_number_24,user_number_25,user_number_26,user_number_27,user_number_28,user_number_29,user_number_3,user_number_30,user_number_31,user_number_32,user_number_33,user_number_34,user_number_35,user_number_36,user_number_37,user_number_38,user_number_39,user_number_4,user_number_40,user_number_5,user_number_6,user_number_7,user_number_8,user_number_9,user_text_1,user_text_10,user_text_11,user_text_12,user_text_13,user_text_14,user_text_15,valve_open_direction,valve_size,valve_turns,valve_type,x,y,fme_basename",Meter,"account_number,amr_id,amr_read_type,amr_type,area_code,asset_id,battery_life,condition_grade,configuration,criticality,current_value,date_cleaned,date_installed,date_read,date_renewed,diameter,elevation,flow_type,gps_survey_date,headloss,inspection_cost,install_cost,lat_distance,lat_pipe_id,lifetime,location,manhole_id,manufacturer,max_flow_headloss,max_flow_rate,measured_max_flow,measured_min_flow,mechanism,meter_reading,min_flow_rate,mobile_uid,model,monitoring_frequency,monitoring_type,node_id,operational_status,owner,photo,photo_filename,photo_ref,planning_status,power_supply,property_id,register_id,register_type,rehab_cost,replace_cost,security,serial_number,sketch,sketch_filename,sketch_ref,soil_type,strainer_fitted,surface_type,survey_date,type,uid,user_date_1,user_date_2,user_date_3,user_date_4,user_date_5,user_number_10,user_number_11,user_number_12,user_number_13,user_number_14,user_number_15,user_number_16,user_number_17,user_number_18,user_number_19,user_number_2,user_number_20,user_number_21,user_number_22,user_number_23,user_number_24,user_number_25,user_number_26,user_number_27,user_number_28,user_number_29,user_number_3,user_number_30,user_number_31,user_number_32,user_number_33,user_number_34,user_number_35,user_number_36,user_number_37,user_number_38,user_number_39,user_number_4,user_number_40,user_number_5,user_number_6,user_number_7,user_number_8,user_number_9,user_text_1,user_text_10,user_text_11,user_text_12,user_text_13,user_text_15,user_text_16,x,y,fme_basename",Pipe,"link_id,access_restrictions,area_code,asset_id,bedding_material,capacity,condition_grade,consequence_comments,consequence_score,construction_method,criticality,criticality_score,cum_sediment,current_value,date_cleaned,date_installed,date_lined,date_renewed,depth_of_cover,ds_node_id,external_diameter,external_protection,external_protection_date,flow_reversals,friction_factor,gps_survey_date,headloss,id,inspection_cost,install_cost,internal_diameter,joint_type,leakage,length,lifetime,likelihood_score,lining_material,lining_type,location,manufacturer,material,max_velocity,min_velocity,mobile_uid,nominal_diameter,operational_status,owner,photo,photo_filename,photo_ref,pipe_class,planning_status,pressure_rating,rail_business_disruption_risk,rehab_cost,rehab_method,replace_cost,risk_score,security,sketch,sketch_filename,sketch_ref,soil_type,surface_type,survey_date,traffic_level,type,uid,us_node_id,use,user_date_1,user_date_2,user_date_3,user_date_4,user_date_5,user_number_1,user_number_10,user_number_11,user_number_12,user_number_13,user_number_14,user_number_15,user_number_16,user_number_17,user_number_18,user_number_19,user_number_2,user_number_20,user_number_21,user_number_22,user_number_23,user_number_24,user_number_25,user_number_26,user_number_27,user_number_28,user_number_29,user_number_3,user_number_30,user_number_31,user_number_32,user_number_33,user_number_34,user_number_35,user_number_36,user_number_37,user_number_38,user_number_39,user_number_4,user_number_40,user_number_5,user_number_6,user_number_7,user_number_8,user_number_9,user_text_1,user_text_10,user_text_11,user_text_12,user_text_13,user_text_9,fme_basename",Tank,"area_code,asset_id,capacity,condition_grade,confined_spaces,criticality,current_value,date_cleaned,date_installed,date_renewed,elevation,gps_survey_date,headloss,inlet_control,inlet_level,inspection_cost,install_cost,lat_distance,lat_pipe_id,lifetime,lining_material,location,manufacturer,material,mobile_uid,node_id,operational_status,outlet_level,owner,photo,photo_filename,photo_ref,planning_status,pump_to_waste,rehab_cost,replace_cost,security,shape,sketch,sketch_filename,sketch_ref,soil_type,surface_type,survey_date,type,uid,user_date_1,user_date_2,user_date_3,user_date_4,user_date_5,user_number_10,user_number_11,user_number_12,user_number_13,user_number_14,user_number_15,user_number_16,user_number_17,user_number_18,user_number_19,user_number_2,user_number_20,user_number_21,user_number_22,user_number_23,user_number_24,user_number_25,user_number_26,user_number_27,user_number_28,user_number_29,user_number_3,user_number_30,user_number_31,user_number_32,user_number_33,user_number_34,user_number_35,user_number_36,user_number_37,user_number_38,user_number_39,user_number_4,user_number_40,user_number_5,user_number_6,user_number_7,user_number_8,user_number_9,user_text_1,user_text_10,user_text_11,user_text_12,user_text_13,user_text_14,user_text_15,user_text_16,x,y,fme_basename",Valve,"area_code,asset_id,condition_grade,configuration,criticality,current_value,date_cleaned,date_installed,date_renewed,date_tagged,diameter,elevation,gps_survey_date,headloss,incoming_pressure,inspection_cost,install_cost,lat_distance,lat_pipe_id,lifetime,location,manhole_id,manufacturer,material,mechanism,mobile_uid,node_id,num_turns,open_direction,operational_role,operational_status,outgoing_pressure,owner,photo,photo_filename,photo_ref,planning_status,position,rehab_cost,replace_cost,security,sketch,sketch_filename,sketch_ref,soil_type,status,surface_type,survey_date,system_type,tagged,uid,user_date_1,user_date_2,user_date_3,user_date_4,user_date_5,user_number_14,user_number_15,user_number_16,user_number_17,user_number_18,user_number_19,user_number_2,user_number_20,user_number_21,user_number_22,user_number_23,user_number_24,user_number_25,user_number_26,user_number_27,user_number_28,user_number_29,user_number_3,user_number_30,user_number_31,user_number_32,user_number_33,user_number_34,user_number_35,user_number_36,user_number_37,user_number_38,user_number_39,user_number_4,user_number_40,user_number_5,user_number_6,user_number_7,user_number_8,user_number_9,user_text_1,user_text_10,user_text_11,user_text_12,user_text_13,user_text_14,user_text_15,valve_box_depth,valve_box_size,valve_box_type,valve_control_type,x,y,fme_basename"
    ATTR_ACCUM_MODE = Merge Initiator and Result
    ATTR_CONFLICT_RES = Use Result
    ATTR_IGNORE_NULLS = No
    COMBINE_GEOM = Use Result
    DATASET = ""$(FME_MF_DIR_ENCODED)watersupply\MIF\Fitting.MIF" "$(FME_MF_DIR_ENCODED)watersupply\MIF\Hydrant.MIF" "$(FME_MF_DIR_ENCODED)watersupply\MIF\Meter.MIF" "$(FME_MF_DIR_ENCODED)watersupply\MIF\Pipe.MIF" "$(FME_MF_DIR_ENCODED)watersupply\MIF\Tank.MIF" "$(FME_MF_DIR_ENCODED)watersupply\MIF\Valve.MIF""
    FORMAT = MIF
    INTERACT = NONE
    MIF_ENCODED_ATTRS = mif_text_string
    MIF_ENCODED_ATTR_NAMES = YES
    MIF_ENCODING = fme-source-encoding
    MIF_MIF_EXPOSE_FORMAT_ATTRS = fme_basename,char(50)
    MIF_PRESERVE_DUPLICATES = YES
    MIF_UNENCODED_ATTR_PREFIX = fme_ mif_
    MIF_USE_SEARCH_ENVELOPE = NO
    ORDER_RESULTS = No
    OUTPUT_FEATURES_DISPLAY = Schema and Data Features
    Hydrant -> EsriReprojector_9
    Meter -> EsriReprojector_10
    Pipe -> EsriReprojector_7
    Valve -> EsriReprojector_12
EsriReprojector_7
    DEST = ESRIWKT|GCS_WGS_1984|GEOGCS["GCS_WGS_1984",DATUM["D_WGS_1984",SPHEROID["WGS_1984",6378137.0,298.257223563]],PRIMEM["Greenwich",0.0],UNIT["Degree",0.0174532925199433]]
    GEOTRANSFORMATION_NAME = NZGD_2000_To_WGS_1984_1
    INTERPOLATION_TYPE_NAME = Nearest Neighbor
    RASTER_CELL_SIZE = Preserve Cells
    RASTER_TOLERANCE = 0.0
    SOURCE = ESRIWKT|NZGD_2000_New_Zealand_Transverse_Mercator|PROJCS["NZGD_2000_New_Zealand_Transverse_Mercator",GEOGCS["GCS_NZGD_2000",DATUM["D_NZGD_2000",SPHEROID["GRS_1980",6378137.0,298.257222101]],PRIMEM["Greenwich",0.0],UNIT["Degree",0.0174532925199433]],PROJECTION["Transverse_Mercator"],PARAMETER["False_Easting",1600000.0],PARAMETER["False_Northing",10000000.0],PARAMETER["Central_Meridian",173.0],PARAMETER["Scale_Factor",0.9996],PARAMETER["Latitude_Of_Origin",0.0],UNIT["Meter",1.0]]
    REPROJECTED -> AttributeKeeper_7
AttributeKeeper_7
    CREATE_BULK_MODE_FEATURES = NO
    KEEP_ATTRS = asset_id,fme_basename,install_cost,length,lifetime,owner,rehab_cost,replace_cost,likelihood_score,uid,current_value,origin_utc,date_installed,material,operational_status,type
    -> AttributeRenamer_8
AttributeRenamer_8
    ATTR_TABLE:
      RENAME_SET_DEFAULT material > pipe_material
      RENAME_SET_DEFAULT date_installed > year_laid
      RENAME_SET_DEFAULT operational_status > status
      RENAME_SET_DEFAULT asset_id > id
    MISSING_INPUT_ATTRS = REMOVE
    -> AttributeCreator_4
EsriReprojector_9
    DEST = ESRIWKT|GCS_WGS_1984|GEOGCS["GCS_WGS_1984",DATUM["D_WGS_1984",SPHEROID["WGS_1984",6378137.0,298.257223563]],PRIMEM["Greenwich",0.0],UNIT["Degree",0.0174532925199433]]
    GEOTRANSFORMATION_NAME = NZGD_2000_To_WGS_1984_1
    INTERPOLATION_TYPE_NAME = Nearest Neighbor
    RASTER_CELL_SIZE = Preserve Cells
    RASTER_TOLERANCE = 0.0
    SOURCE = ESRIWKT|NZGD_2000_New_Zealand_Transverse_Mercator|PROJCS["NZGD_2000_New_Zealand_Transverse_Mercator",GEOGCS["GCS_NZGD_2000",DATUM["D_NZGD_2000",SPHEROID["GRS_1980",6378137.0,298.257222101]],PRIMEM["Greenwich",0.0],UNIT["Degree",0.0174532925199433]],PROJECTION["Transverse_Mercator"],PARAMETER["False_Easting",1600000.0],PARAMETER["False_Northing",10000000.0],PARAMETER["Central_Meridian",173.0],PARAMETER["Scale_Factor",0.9996],PARAMETER["Latitude_Of_Origin",0.0],UNIT["Meter",1.0]]
    REPROJECTED -> AttributeKeeper_8
EsriReprojector_10
    DEST = ESRIWKT|GCS_WGS_1984|GEOGCS["GCS_WGS_1984",DATUM["D_WGS_1984",SPHEROID["WGS_1984",6378137.0,298.257223563]],PRIMEM["Greenwich",0.0],UNIT["Degree",0.0174532925199433]]
    GEOTRANSFORMATION_NAME = NZGD_2000_To_WGS_1984_1
    INTERPOLATION_TYPE_NAME = Nearest Neighbor
    RASTER_CELL_SIZE = Preserve Cells
    RASTER_TOLERANCE = 0.0
    SOURCE = ESRIWKT|NZGD_2000_New_Zealand_Transverse_Mercator|PROJCS["NZGD_2000_New_Zealand_Transverse_Mercator",GEOGCS["GCS_NZGD_2000",DATUM["D_NZGD_2000",SPHEROID["GRS_1980",6378137.0,298.257222101]],PRIMEM["Greenwich",0.0],UNIT["Degree",0.0174532925199433]],PROJECTION["Transverse_Mercator"],PARAMETER["False_Easting",1600000.0],PARAMETER["False_Northing",10000000.0],PARAMETER["Central_Meridian",173.0],PARAMETER["Scale_Factor",0.9996],PARAMETER["Latitude_Of_Origin",0.0],UNIT["Meter",1.0]]
    REPROJECTED -> AttributeKeeper_8
EsriReprojector_12
    DEST = ESRIWKT|GCS_WGS_1984|GEOGCS["GCS_WGS_1984",DATUM["D_WGS_1984",SPHEROID["WGS_1984",6378137.0,298.257223563]],PRIMEM["Greenwich",0.0],UNIT["Degree",0.0174532925199433]]
    GEOTRANSFORMATION_NAME = NZGD_2000_To_WGS_1984_1
    INTERPOLATION_TYPE_NAME = Nearest Neighbor
    RASTER_CELL_SIZE = Preserve Cells
    RASTER_TOLERANCE = 0.0
    SOURCE = ESRIWKT|NZGD_2000_New_Zealand_Transverse_Mercator|PROJCS["NZGD_2000_New_Zealand_Transverse_Mercator",GEOGCS["GCS_NZGD_2000",DATUM["D_NZGD_2000",SPHEROID["GRS_1980",6378137.0,298.257222101]],PRIMEM["Greenwich",0.0],UNIT["Degree",0.0174532925199433]],PROJECTION["Transverse_Mercator"],PARAMETER["False_Easting",1600000.0],PARAMETER["False_Northing",10000000.0],PARAMETER["Central_Meridian",173.0],PARAMETER["Scale_Factor",0.9996],PARAMETER["Latitude_Of_Origin",0.0],UNIT["Meter",1.0]]
    REPROJECTED -> AttributeKeeper_8
AttributeKeeper_8
    CREATE_BULK_MODE_FEATURES = NO
    KEEP_ATTRS = fme_basename,install_cost,lifetime,owner,rehab_cost,replace_cost,x,y,uid,node_id,current_value,origin_utc,date_installed,operational_status,type
    -> AttributeRenamer_9
AttributeRenamer_9
    ATTR_TABLE:
      RENAME_SET_DEFAULT date_installed > year_laid
      RENAME_SET_DEFAULT operational_status > status
      RENAME_SET_DEFAULT node_id > id
    MISSING_INPUT_ATTRS = REMOVE
    -> Tester
Note: Tester [Tester] / Test Clauses: Left ValueOperatorRight Value@Value(x)Attribute Has a ValueAdvanced: / Preserve Feature Order: Per Output Port
Tester
    BOOL_OP = OR
    TEST_CLAUSE = TEST x ATTRIBUTE_HAS_A_VALUE ""
    TEST_MODE = TEST
    PASSED -> AttributeCreator_4
AttributeCreator_4
    ATTR_TABLE = SET_TO system (buffer) = ws
    -> Junction_17
Junction_17
    -> Junction_18

Bookmark: transform: create coords for geometry
Junction_18
    -> CenterPointReplacer
Junction_4
    -> CenterPointReplacer
Junction_16
    -> CenterPointReplacer
CenterPointReplacer
    POINTTYPE = CENTER
    POINT -> CoordinateExtractor
    UNTOUCHED -> CenterPointReplacer__Rejected_
CoordinateExtractor
    LIST_NAME = _indices
    MODE = All Coordinates
    -> AttributeCreator
AttributeCreator
    ATTR_TABLE:
      SET_TO x (varchar(200)) = @Value(_indices{0}.x)
      SET_TO y (varchar(200)) = @Value(_indices{0}.y)
    -> AttributeRemover
AttributeRemover
    REMOVE_ATTRS = _indices{0}.x,_indices{0}.y,_indices{0}.z
    -> Tester_4
Note: add a bounding box and remove dumb testers
Tester_4
    BOOL_OP = OR
    TEST_CLAUSE = TEST @Value(y) != 90
    TEST_MODE = TEST
    PASSED -> Junction_7
Junction_7
    -> Junction_8
Note: pipes with no length filtered
CenterPointReplacer__Rejected_: Logger
    LOG_FEATURE = LOG_ONLY
    MAXCOORDS = 20
    MAXFEATS = 20
    MESSAGE = Feature is:
    SEVERITY = INFO

Bookmark: extract: wastewater
Junction_3
    -> _wastewater [INITIATOR]
_wastewater: FeatureReader
    ATTRIBUTES = "Connection pipe","link_id,asset_id,branch_id,condition_code,condition_score,criticality,current_value,date_cleaned,description,diameter,ds_image_filename,ds_image_ref,ds_node_id,ground_level,id,inspection_cost,install_cost,int_pipe_CH2MHill_maint_scr,int_pipe_CH2MHill_scr,int_pipe_CH2MHill_struc_scr,internal_pipe_score,length,lifetime,lining_material,lining_type,location,mobile_uid,owner,pipe_material,property_id,rehab_cost,replace_cost,service_condition_score,shape,status,survey_date,system_type,type,uid,us_image_filename,us_image_ref,us_node_id,user_date_1,user_date_2,user_date_3,user_date_4,user_date_5,user_number_16,user_number_17,user_number_18,user_number_19,user_number_2,user_number_20,user_number_21,user_number_22,user_number_23,user_number_24,user_number_25,user_number_26,user_number_27,user_number_28,user_number_29,user_number_3,user_number_30,user_number_31,user_number_32,user_number_33,user_number_34,user_number_35,user_number_36,user_number_37,user_number_38,user_number_39,user_number_4,user_number_40,user_number_5,user_number_6,user_number_7,user_number_8,user_number_9,user_text_1,user_text_10,user_text_11,user_text_12,user_text_13,user_text_14,user_text_15,user_text_16,x_end,x_start,y_end,y_start,year_laid,year_renew,z_end,z_start,fme_basename",Node,"access_action,access_time,access_type,adjustment_ring_height,adjustment_ring_material,adjustment_ring_type,asset_id,attend_to_bench,attend_to_chamber,attend_to_cover,attend_to_other,attend_to_shaft,attend_to_step,bench_lining,bench_material,bench_present,category,CH2MHill_overall_ii_grade,CH2MHill_overall_sii_grade,CH2MHill_overall_total_grad,chamber_condition,chamber_construction,chamber_dim,chamber_dim_2,chamber_floor_depth,chamber_shape,channel_exposure,channel_installed,channel_material,channel_type,chimney_clear_opening,chimney_depth,chimney_ini,chimney_lining_exterior,chimney_lining_interior,chimney_material1,chimney_material2,city,clear_opening,condition_grade,cone_depth,cone_lining_exterior,cone_lining_interior,cone_material,cone_type,coordinate_system,cover_assembly,cover_bearing_surface_dia,cover_bearing_surface_dia_width,cover_condition,cover_condition_boltsmissing,cover_condition_broken,cover_condition_corroded,cover_condition_cracked,cover_condition_missing,cover_condition_restraint_defect,cover_condition_restraint_miss,cover_condition_sound,cover_dim,cover_dim_2,cover_duty,cover_frame_fit,cover_hinged,cover_insert_type,cover_level,cover_locked,cover_material,cover_shape,cover_type_bolted,cover_type_gasketed,cover_type_hatch_double,cover_type_hatch_single,cover_type_inner_cover,cover_type_lamphole,cover_type_locking,cover_type_solid,cover_type_vented,criticality,cross_slope,current_value,debris,drainage_area,drainage_code,flow_depth,frame_bearing_surface_depth,frame_bearing_surface_width,frame_clear_open_diam,frame_condition_broken,frame_condition_coated,frame_condition_corroded,frame_condition_cracked,frame_condition_missing,frame_condition_sound,frame_depth,frame_material,frame_offset_distance,frame_seal_inflow,gas_type,gps_survey_date,grade_to_invert,grate_length,grate_width,ground_level,gutter_depression,hole_diameter,hole_number,inlet_type,insert_condition_corroded,insert_condition_cracked,insert_condition_insertfell,insert_condition_leaking,insert_condition_poorlyfitting,insert_condition_sound,inspection_cost,inspection_status,install_cost,internal_image_ref,lat_circ_location,lat_distance,lat_ds_node_id,lat_link_suffix,lat_us_node_id,lateral_depression,leveler_condition,leveler_material,lifetime,location,location_code,location_details,location_image_ref,location_sketch_ref,maintenance_condition,mobile_uid,node_id,node_type,num_ladders,num_landings,num_regulating,num_steps,opening_height,opening_length,owner,plan_sketch_ref,po_number,potential_for_runoff,rehab_cost,replace_cost,rim_to_grade,rim_to_invert,ring_condition_broken,ring_condition_corroded,ring_condition_cracked,ring_condition_leaking,ring_condition_poorinstall,ring_condition_sound,seal_condition_cracked,seal_condition_loose,seal_condition_missing,seal_condition_offset,seal_condition_sound,security,shaft_access,shaft_condition,shaft_depth,shaft_dim,shaft_dim_2,shaft_material,side_entry,silt_depth,site_condition,site_managed_by,soffit_type,status,step_material,street,surcharge_height,surface_type_asphalt,surface_type_concretecollar,surface_type_concretepavement,surface_type_grassdirt,surface_type_gravel,surface_type_other,survey_date,system_type,toxic_atmosphere,uid,vermin,wall_bysize,wall_depth,wall_diam,wall_lining_exterior,wall_lining_interior,wall_material,x,y,year_laid,year_renewed,fme_basename",Pipe,"link_id,access_restrictions,asset_id,backdrop_diam,branch_id,capacity,condition_code,condition_score,consequence_comments,consequence_score,criticality,current_value,date_cleaned,drainage_code,ds_depth_from_cover,ds_height,ds_image_filename,ds_image_ref,ds_invert,ds_lining_material,ds_lining_type,ds_node_id,ds_pipe_material,ds_shape,ds_width,flow_control,gradient,ground_type,ground_water_risk,height,inspection_cost,install_cost,int_pipe_CH2MHill_maint_scr,int_pipe_CH2MHill_scr,int_pipe_CH2MHill_struc_scr,internal_pipe_score,length,lifetime,likelihood_score,lining_material,lining_type,link_suffix,location,mobile_uid,odour_nuisance_risk,owner,pipe_class,pipe_material,pipe_type,property_flooding_risk,rail_business_disruption_risk,rehab_cost,repair_cost,repair_cost_risk,replace_cost,risk_score,security,service_condition_score,shape,site_condition,status,surface_water_risk,survey_date,system_type,taking_off_reference,traffic_delay_risk,traffic_level,uid,unit_length,us_depth_from_cover,us_image_filename,us_image_ref,us_invert,us_node_id,user_date_1,user_date_2,user_date_3,user_date_4,user_date_5,user_number_1,user_number_10,user_number_11,user_number_12,user_number_13,user_number_14,user_number_15,user_number_16,user_number_17,user_number_18,user_number_19,user_number_2,user_number_20,user_number_21,user_number_22,user_number_23,user_number_24,user_number_25,user_number_26,user_number_27,user_number_28,user_number_29,user_number_3,user_number_30,user_number_31,user_number_32,user_number_33,user_number_34,user_number_35,user_number_36,user_number_37,user_number_38,user_number_39,user_number_4,user_number_40,user_number_5,user_number_6,user_number_7,user_number_8,user_number_9,user_text_1,user_text_10,user_text_12,user_text_13,user_text_14,user_text_15,width,year_laid,year_renew,fme_basename"
    ATTR_ACCUM_MODE = Merge Initiator and Result
    ATTR_CONFLICT_RES = Use Result
    ATTR_IGNORE_NULLS = No
    COMBINE_GEOM = Use Result
    DATASET = ""$(FME_MF_DIR_ENCODED)wastewater\MIF\Connection pipe.MIF" "$(FME_MF_DIR_ENCODED)wastewater\MIF\Node.MIF" "$(FME_MF_DIR_ENCODED)wastewater\MIF\Pipe.MIF""
    FORMAT = MIF
    INTERACT = NONE
    MIF_ENCODED_ATTRS = mif_text_string
    MIF_ENCODED_ATTR_NAMES = YES
    MIF_ENCODING = fme-source-encoding
    MIF_MIF_EXPOSE_FORMAT_ATTRS = fme_basename,char(50)
    MIF_PRESERVE_DUPLICATES = YES
    MIF_UNENCODED_ATTR_PREFIX = fme_ mif_
    MIF_USE_SEARCH_ENVELOPE = NO
    ORDER_RESULTS = No
    OUTPUT_FEATURES_DISPLAY = Schema and Data Features
    Connection pipe -> EsriReprojector_3
    Node -> EsriReprojector_2
    Pipe -> EsriReprojector
EsriReprojector_2
    DEST = ESRIWKT|GCS_WGS_1984|GEOGCS["GCS_WGS_1984",DATUM["D_WGS_1984",SPHEROID["WGS_1984",6378137.0,298.257223563]],PRIMEM["Greenwich",0.0],UNIT["Degree",0.0174532925199433]]
    GEOTRANSFORMATION_NAME = NZGD_2000_To_WGS_1984_1
    INTERPOLATION_TYPE_NAME = Nearest Neighbor
    RASTER_CELL_SIZE = Preserve Cells
    RASTER_TOLERANCE = 0.0
    SOURCE = ESRIWKT|NZGD_2000_New_Zealand_Transverse_Mercator|PROJCS["NZGD_2000_New_Zealand_Transverse_Mercator",GEOGCS["GCS_NZGD_2000",DATUM["D_NZGD_2000",SPHEROID["GRS_1980",6378137.0,298.257222101]],PRIMEM["Greenwich",0.0],UNIT["Degree",0.0174532925199433]],PROJECTION["Transverse_Mercator"],PARAMETER["False_Easting",1600000.0],PARAMETER["False_Northing",10000000.0],PARAMETER["Central_Meridian",173.0],PARAMETER["Scale_Factor",0.9996],PARAMETER["Latitude_Of_Origin",0.0],UNIT["Meter",1.0]]
    REPROJECTED -> AttributeKeeper_3
AttributeKeeper_3
    CREATE_BULK_MODE_FEATURES = NO
    KEEP_ATTRS = asset_id,fme_basename,install_cost,lifetime,owner,rehab_cost,replace_cost,status,year_laid,x,y,uid,node_id,current_value,node_type,origin_utc
    -> AttributeRenamer_2
AttributeRenamer_2
    ATTR_TABLE:
      RENAME_SET_DEFAULT node_type > type
      RENAME_SET_DEFAULT node_id > id
    MISSING_INPUT_ATTRS = REMOVE
    -> Tester_2
Note: Tester_2 [Tester] / Test Clauses: Left ValueOperatorRight Value@Value(x)!=0Advanced: / Preserve Feature Order: Per Output Port
Tester_2
    BOOL_OP = OR
    TEST_CLAUSE = TEST @Value(x) != 0
    TEST_MODE = TEST
    PASSED -> AttributeCreator_2
EsriReprojector
    DEST = ESRIWKT|GCS_WGS_1984|GEOGCS["GCS_WGS_1984",DATUM["D_WGS_1984",SPHEROID["WGS_1984",6378137.0,298.257223563]],PRIMEM["Greenwich",0.0],UNIT["Degree",0.0174532925199433]]
    GEOTRANSFORMATION_NAME = NZGD_2000_To_WGS_1984_1
    INTERPOLATION_TYPE_NAME = Nearest Neighbor
    RASTER_CELL_SIZE = Preserve Cells
    RASTER_TOLERANCE = 0.0
    SOURCE = ESRIWKT|NZGD_2000_New_Zealand_Transverse_Mercator|PROJCS["NZGD_2000_New_Zealand_Transverse_Mercator",GEOGCS["GCS_NZGD_2000",DATUM["D_NZGD_2000",SPHEROID["GRS_1980",6378137.0,298.257222101]],PRIMEM["Greenwich",0.0],UNIT["Degree",0.0174532925199433]],PROJECTION["Transverse_Mercator"],PARAMETER["False_Easting",1600000.0],PARAMETER["False_Northing",10000000.0],PARAMETER["Central_Meridian",173.0],PARAMETER["Scale_Factor",0.9996],PARAMETER["Latitude_Of_Origin",0.0],UNIT["Meter",1.0]]
    REPROJECTED -> AttributeKeeper_2
AttributeKeeper_2
    CREATE_BULK_MODE_FEATURES = NO
    KEEP_ATTRS = asset_id,fme_basename,install_cost,length,lifetime,owner,pipe_material,rehab_cost,replace_cost,status,year_laid,likelihood_score,uid,current_value,pipe_type,origin_utc
    -> AttributeRenamer_3
AttributeRenamer_3
    ATTR_TABLE:
      RENAME_SET_DEFAULT pipe_type > type
      RENAME_SET_DEFAULT asset_id > id
    MISSING_INPUT_ATTRS = REMOVE
    -> AttributeCreator_2
EsriReprojector_3
    DEST = ESRIWKT|GCS_WGS_1984|GEOGCS["GCS_WGS_1984",DATUM["D_WGS_1984",SPHEROID["WGS_1984",6378137.0,298.257223563]],PRIMEM["Greenwich",0.0],UNIT["Degree",0.0174532925199433]]
    GEOTRANSFORMATION_NAME = NZGD_2000_To_WGS_1984_1
    INTERPOLATION_TYPE_NAME = Nearest Neighbor
    RASTER_CELL_SIZE = Preserve Cells
    RASTER_TOLERANCE = 0.0
    SOURCE = ESRIWKT|NZGD_2000_New_Zealand_Transverse_Mercator|PROJCS["NZGD_2000_New_Zealand_Transverse_Mercator",GEOGCS["GCS_NZGD_2000",DATUM["D_NZGD_2000",SPHEROID["GRS_1980",6378137.0,298.257222101]],PRIMEM["Greenwich",0.0],UNIT["Degree",0.0174532925199433]],PROJECTION["Transverse_Mercator"],PARAMETER["False_Easting",1600000.0],PARAMETER["False_Northing",10000000.0],PARAMETER["Central_Meridian",173.0],PARAMETER["Scale_Factor",0.9996],PARAMETER["Latitude_Of_Origin",0.0],UNIT["Meter",1.0]]
    REPROJECTED -> AttributeKeeper
AttributeKeeper
    CREATE_BULK_MODE_FEATURES = NO
    KEEP_ATTRS = asset_id,fme_basename,install_cost,length,lifetime,owner,pipe_material,rehab_cost,replace_cost,status,year_laid,uid,current_value,type,origin_utc,condition_score
    -> AttributeRenamer_4
AttributeRenamer_4
    ATTR_TABLE:
      RENAME_SET_DEFAULT asset_id > id
      RENAME_SET_DEFAULT condition_score > likelihood_score
    MISSING_INPUT_ATTRS = REMOVE
    -> AttributeCreator_2
AttributeCreator_2
    ATTR_TABLE = SET_TO system (buffer) = ww
    -> Junction_2
Junction_2
    -> Junction_4

Bookmark: extract: stormwater
Junction_14
    -> _stormwater [INITIATOR]
_stormwater: FeatureReader
    ATTRIBUTES = "Connection pipe","link_id,asset_id,branch_id,condition_code,condition_score,criticality,current_value,date_cleaned,description,diameter,ds_image_filename,ds_image_ref,ds_node_id,ground_level,id,inspection_cost,install_cost,int_pipe_CH2MHill_maint_scr,int_pipe_CH2MHill_scr,int_pipe_CH2MHill_struc_scr,internal_pipe_score,length,lifetime,lining_material,lining_type,location,mobile_uid,owner,pipe_material,property_id,rehab_cost,replace_cost,service_condition_score,shape,status,survey_date,system_type,type,uid,us_image_filename,us_image_ref,us_node_id,user_date_1,user_date_2,user_date_3,user_date_4,user_date_5,user_number_16,user_number_17,user_number_18,user_number_19,user_number_2,user_number_20,user_number_21,user_number_22,user_number_23,user_number_24,user_number_25,user_number_26,user_number_27,user_number_28,user_number_29,user_number_3,user_number_30,user_number_31,user_number_32,user_number_33,user_number_34,user_number_35,user_number_36,user_number_37,user_number_38,user_number_39,user_number_4,user_number_40,user_number_5,user_number_6,user_number_7,user_number_8,user_number_9,user_text_1,user_text_10,user_text_11,user_text_12,user_text_13,user_text_14,user_text_15,user_text_16,x_end,x_start,y_end,y_start,year_laid,year_renew,z_end,z_start,fme_basename",Node,"access_action,access_time,access_type,adjustment_ring_height,adjustment_ring_material,adjustment_ring_type,asset_id,attend_to_bench,attend_to_chamber,attend_to_cover,attend_to_other,attend_to_shaft,attend_to_step,bench_lining,bench_material,bench_present,category,CH2MHill_overall_ii_grade,CH2MHill_overall_sii_grade,CH2MHill_overall_total_grad,chamber_condition,chamber_construction,chamber_dim,chamber_dim_2,chamber_floor_depth,chamber_shape,channel_exposure,channel_installed,channel_material,channel_type,chimney_clear_opening,chimney_depth,chimney_ini,chimney_lining_exterior,chimney_lining_interior,chimney_material1,chimney_material2,city,clear_opening,condition_grade,cone_depth,cone_lining_exterior,cone_lining_interior,cone_material,cone_type,coordinate_system,cover_assembly,cover_bearing_surface_dia,cover_bearing_surface_dia_width,cover_condition,cover_condition_boltsmissing,cover_condition_broken,cover_condition_corroded,cover_condition_cracked,cover_condition_missing,cover_condition_restraint_defect,cover_condition_restraint_miss,cover_condition_sound,cover_dim,cover_dim_2,cover_duty,cover_frame_fit,cover_hinged,cover_insert_type,cover_level,cover_locked,cover_material,cover_shape,cover_type_bolted,cover_type_gasketed,cover_type_hatch_double,cover_type_hatch_single,cover_type_inner_cover,cover_type_lamphole,cover_type_locking,cover_type_solid,cover_type_vented,criticality,cross_slope,current_value,debris,drainage_area,drainage_code,flow_depth,frame_bearing_surface_depth,frame_bearing_surface_width,frame_clear_open_diam,frame_condition_broken,frame_condition_coated,frame_condition_corroded,frame_condition_cracked,frame_condition_missing,frame_condition_sound,frame_depth,frame_material,frame_offset_distance,frame_seal_inflow,gas_type,gps_survey_date,grade_to_invert,grate_length,grate_width,ground_level,gutter_depression,hole_diameter,hole_number,inlet_type,insert_condition_corroded,insert_condition_cracked,insert_condition_insertfell,insert_condition_leaking,insert_condition_poorlyfitting,insert_condition_sound,inspection_cost,inspection_status,install_cost,internal_image_ref,lat_circ_location,lat_distance,lat_ds_node_id,lat_link_suffix,lat_us_node_id,lateral_depression,leveler_condition,leveler_material,lifetime,location,location_code,location_details,location_image_ref,location_sketch_ref,maintenance_condition,mobile_uid,node_id,node_type,num_ladders,num_landings,num_regulating,num_steps,opening_height,opening_length,owner,plan_sketch_ref,po_number,potential_for_runoff,rehab_cost,replace_cost,rim_to_grade,rim_to_invert,ring_condition_broken,ring_condition_corroded,ring_condition_cracked,ring_condition_leaking,ring_condition_poorinstall,ring_condition_sound,seal_condition_cracked,seal_condition_loose,seal_condition_missing,seal_condition_offset,seal_condition_sound,security,shaft_access,shaft_condition,shaft_depth,shaft_dim,shaft_dim_2,shaft_material,side_entry,silt_depth,site_condition,site_managed_by,soffit_type,status,step_material,street,surcharge_height,surface_type_asphalt,surface_type_concretecollar,surface_type_concretepavement,surface_type_grassdirt,surface_type_gravel,surface_type_other,survey_date,system_type,toxic_atmosphere,uid,vermin,wall_bysize,wall_depth,wall_diam,wall_lining_exterior,wall_lining_interior,wall_material,x,y,year_laid,year_renewed,fme_basename",Pipe,"link_id,access_restrictions,asset_id,backdrop_diam,branch_id,capacity,condition_code,condition_score,consequence_comments,consequence_score,criticality,current_value,date_cleaned,drainage_code,ds_depth_from_cover,ds_height,ds_image_filename,ds_image_ref,ds_invert,ds_lining_material,ds_lining_type,ds_node_id,ds_pipe_material,ds_shape,ds_width,flow_control,gradient,ground_type,ground_water_risk,height,inspection_cost,install_cost,int_pipe_CH2MHill_maint_scr,int_pipe_CH2MHill_scr,int_pipe_CH2MHill_struc_scr,internal_pipe_score,length,lifetime,likelihood_score,lining_material,lining_type,link_suffix,location,mobile_uid,odour_nuisance_risk,owner,pipe_class,pipe_material,pipe_type,property_flooding_risk,rail_business_disruption_risk,rehab_cost,repair_cost,repair_cost_risk,replace_cost,risk_score,security,service_condition_score,shape,site_condition,status,surface_water_risk,survey_date,system_type,taking_off_reference,traffic_delay_risk,traffic_level,uid,unit_length,us_depth_from_cover,us_image_filename,us_image_ref,us_invert,us_node_id,user_date_1,user_date_2,user_date_3,user_date_4,user_date_5,user_number_1,user_number_10,user_number_11,user_number_12,user_number_13,user_number_14,user_number_15,user_number_16,user_number_17,user_number_18,user_number_19,user_number_2,user_number_20,user_number_21,user_number_22,user_number_23,user_number_24,user_number_25,user_number_26,user_number_27,user_number_28,user_number_29,user_number_3,user_number_30,user_number_31,user_number_32,user_number_33,user_number_34,user_number_35,user_number_36,user_number_37,user_number_38,user_number_39,user_number_4,user_number_40,user_number_5,user_number_6,user_number_7,user_number_8,user_number_9,user_text_1,user_text_10,user_text_12,user_text_13,user_text_14,user_text_15,width,year_laid,year_renew,fme_basename"
    ATTR_ACCUM_MODE = Merge Initiator and Result
    ATTR_CONFLICT_RES = Use Result
    ATTR_IGNORE_NULLS = No
    COMBINE_GEOM = Use Result
    DATASET = ""$(FME_MF_DIR_ENCODED)stormwater\MIF\Connection pipe.MIF" "$(FME_MF_DIR_ENCODED)stormwater\MIF\Node.MIF" "$(FME_MF_DIR_ENCODED)stormwater\MIF\Pipe.MIF""
    FORMAT = MIF
    INTERACT = NONE
    MIF_ENCODED_ATTRS = mif_text_string
    MIF_ENCODED_ATTR_NAMES = YES
    MIF_ENCODING = fme-source-encoding
    MIF_MIF_EXPOSE_FORMAT_ATTRS = fme_basename,char(50)
    MIF_PRESERVE_DUPLICATES = YES
    MIF_UNENCODED_ATTR_PREFIX = fme_ mif_
    MIF_USE_SEARCH_ENVELOPE = NO
    ORDER_RESULTS = No
    OUTPUT_FEATURES_DISPLAY = Schema and Data Features
    Connection pipe -> EsriReprojector_6
    Node -> EsriReprojector_4
    Pipe -> EsriReprojector_5
EsriReprojector_4
    DEST = ESRIWKT|GCS_WGS_1984|GEOGCS["GCS_WGS_1984",DATUM["D_WGS_1984",SPHEROID["WGS_1984",6378137.0,298.257223563]],PRIMEM["Greenwich",0.0],UNIT["Degree",0.0174532925199433]]
    GEOTRANSFORMATION_NAME = NZGD_2000_To_WGS_1984_1
    INTERPOLATION_TYPE_NAME = Nearest Neighbor
    RASTER_CELL_SIZE = Preserve Cells
    RASTER_TOLERANCE = 0.0
    SOURCE = ESRIWKT|NZGD_2000_New_Zealand_Transverse_Mercator|PROJCS["NZGD_2000_New_Zealand_Transverse_Mercator",GEOGCS["GCS_NZGD_2000",DATUM["D_NZGD_2000",SPHEROID["GRS_1980",6378137.0,298.257222101]],PRIMEM["Greenwich",0.0],UNIT["Degree",0.0174532925199433]],PROJECTION["Transverse_Mercator"],PARAMETER["False_Easting",1600000.0],PARAMETER["False_Northing",10000000.0],PARAMETER["Central_Meridian",173.0],PARAMETER["Scale_Factor",0.9996],PARAMETER["Latitude_Of_Origin",0.0],UNIT["Meter",1.0]]
    REPROJECTED -> AttributeKeeper_6
AttributeKeeper_6
    CREATE_BULK_MODE_FEATURES = NO
    KEEP_ATTRS = asset_id,fme_basename,install_cost,lifetime,owner,rehab_cost,replace_cost,status,year_laid,x,y,uid,node_id,current_value,node_type,origin_utc
    -> AttributeRenamer_5
AttributeRenamer_5
    ATTR_TABLE:
      RENAME_SET_DEFAULT node_type > type
      RENAME_SET_DEFAULT node_id > id
    MISSING_INPUT_ATTRS = REMOVE
    -> Tester_3
Note: Tester_3 [Tester] / Test Clauses: Left ValueOperatorRight Value@Value(x)!=0Advanced: / Preserve Feature Order: Per Output Port
Tester_3
    BOOL_OP = OR
    TEST_CLAUSE = TEST @Value(x) != 0
    TEST_MODE = TEST
    PASSED -> AttributeCreator_3
EsriReprojector_5
    DEST = ESRIWKT|GCS_WGS_1984|GEOGCS["GCS_WGS_1984",DATUM["D_WGS_1984",SPHEROID["WGS_1984",6378137.0,298.257223563]],PRIMEM["Greenwich",0.0],UNIT["Degree",0.0174532925199433]]
    GEOTRANSFORMATION_NAME = NZGD_2000_To_WGS_1984_1
    INTERPOLATION_TYPE_NAME = Nearest Neighbor
    RASTER_CELL_SIZE = Preserve Cells
    RASTER_TOLERANCE = 0.0
    SOURCE = ESRIWKT|NZGD_2000_New_Zealand_Transverse_Mercator|PROJCS["NZGD_2000_New_Zealand_Transverse_Mercator",GEOGCS["GCS_NZGD_2000",DATUM["D_NZGD_2000",SPHEROID["GRS_1980",6378137.0,298.257222101]],PRIMEM["Greenwich",0.0],UNIT["Degree",0.0174532925199433]],PROJECTION["Transverse_Mercator"],PARAMETER["False_Easting",1600000.0],PARAMETER["False_Northing",10000000.0],PARAMETER["Central_Meridian",173.0],PARAMETER["Scale_Factor",0.9996],PARAMETER["Latitude_Of_Origin",0.0],UNIT["Meter",1.0]]
    REPROJECTED -> AttributeKeeper_5
AttributeKeeper_5
    CREATE_BULK_MODE_FEATURES = NO
    KEEP_ATTRS = asset_id,fme_basename,install_cost,length,lifetime,owner,pipe_material,rehab_cost,replace_cost,status,year_laid,likelihood_score,uid,current_value,pipe_type,origin_utc
    -> AttributeRenamer_6
AttributeRenamer_6
    ATTR_TABLE:
      RENAME_SET_DEFAULT pipe_type > type
      RENAME_SET_DEFAULT asset_id > id
    MISSING_INPUT_ATTRS = REMOVE
    -> AttributeCreator_3
EsriReprojector_6
    DEST = ESRIWKT|GCS_WGS_1984|GEOGCS["GCS_WGS_1984",DATUM["D_WGS_1984",SPHEROID["WGS_1984",6378137.0,298.257223563]],PRIMEM["Greenwich",0.0],UNIT["Degree",0.0174532925199433]]
    GEOTRANSFORMATION_NAME = NZGD_2000_To_WGS_1984_1
    INTERPOLATION_TYPE_NAME = Nearest Neighbor
    RASTER_CELL_SIZE = Preserve Cells
    RASTER_TOLERANCE = 0.0
    SOURCE = ESRIWKT|NZGD_2000_New_Zealand_Transverse_Mercator|PROJCS["NZGD_2000_New_Zealand_Transverse_Mercator",GEOGCS["GCS_NZGD_2000",DATUM["D_NZGD_2000",SPHEROID["GRS_1980",6378137.0,298.257222101]],PRIMEM["Greenwich",0.0],UNIT["Degree",0.0174532925199433]],PROJECTION["Transverse_Mercator"],PARAMETER["False_Easting",1600000.0],PARAMETER["False_Northing",10000000.0],PARAMETER["Central_Meridian",173.0],PARAMETER["Scale_Factor",0.9996],PARAMETER["Latitude_Of_Origin",0.0],UNIT["Meter",1.0]]
    REPROJECTED -> AttributeKeeper_4
AttributeKeeper_4
    CREATE_BULK_MODE_FEATURES = NO
    KEEP_ATTRS = asset_id,fme_basename,install_cost,length,lifetime,owner,pipe_material,rehab_cost,replace_cost,status,year_laid,uid,current_value,type,origin_utc,condition_score
    -> AttributeRenamer_7
AttributeRenamer_7
    ATTR_TABLE:
      RENAME_SET_DEFAULT asset_id > id
      RENAME_SET_DEFAULT condition_score > likelihood_score
    MISSING_INPUT_ATTRS = REMOVE
    -> AttributeCreator_3
AttributeCreator_3
    ATTR_TABLE = SET_TO system (buffer) = sw
    -> Junction_15
Junction_15
    -> Junction_16

Bookmark: transform: prep table to for loading to topojson
Junction_8
    -> AttributeManager
AttributeManager
    ATTR_TABLE:
      RENAME_SET_VALUE fme_basename > basename (varchar(50))
      REMOVE asset_id (varchar(40))
      RENAME_SET_VALUE pipe_material > material (varchar(64))
      RENAME_SET_VALUE length > units (real64) = FME_CONDITIONAL:DEFAULT_VALUE'1'BOOL_OP;OR;COMPOSITE_TEST;1;TEST units ATTRIBUTE_HAS_A_VALUE _FME_BLANK_STRING_'@Value(units)'FME_NUM_CONDITIONS2___
      REMOVE _indices{}.x (real64)
      REMOVE _indices{}.y (real64)
      REMOVE _indices{}.z (real64)
    -> DateTimeConverter_2
DateTimeConverter_2
    DATETIME_ATTR = year_laid
    IN_FORMAT = %d/%m/%Y
    OUT_FORMAT = %Y%m%d%H%M%S
    PASSTHROUGH = NO
    REPAIR_INPUT = YES
    -> DateTimeConverter
    <REJECTED> -> DateTimeConverter
DateTimeConverter
    DATETIME_ATTR = origin_utc year_laid
    IN_FORMAT = FME
    OUT_FORMAT = %Y-%m-%d
    PASSTHROUGH = NO
    REPAIR_INPUT = YES
    -> Junction_9
    <REJECTED> -> Junction_9
Junction_9
    -> Junction_10

Bookmark: load: 2topojson
Junction_10
    -> _csv [Output]
_csv: FeatureWriter
    CSV2_COORDINATE_SYSTEM_GRANULARITY = FEATURE_TYPE
    CSV2_DELIMITER = ,
    CSV2_ENCODING = UTF-8
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = if_needed
    CSV2_QUALIFY_FIELD_VALUES = if_needed
    CSV2_ROW_TERMINATION = System
    CSV2_TREAT_EMBEDDED_FIELD_QUALIFIERS_AS_UNSAFE = Yes
    CSV2_WRITE_BOM_FOR_UNICODE = Yes
    CSV2_WRITE_FIELD_NAMES = firstrow
    CSV2_WRITE_SCHEMA_FILE = NO
    DATASET = $(FME_MF_DIR_ENCODED)imports\iam_network
    DATASET_ATTR = _dataset
    FEATURE_TYPE_LIST_ATTR = _feature_types
    FORMAT = CSV2
    TOTAL_FEATURES_WRITTEN_ATTR = _total_features_written
