FME workspace Z wastewater - export2agol - network.fmw

Parameters:
- DestDataset_ARCGISPORTALFEATURES = https://gis.qldc.govt.nz/portal   # Portal URL
- DestDataset_ARCGISPORTALFEATURES_5 = https://gis.qldc.govt.nz/portal   # Portal URL
- DestDataset_ARCGISPORTALFEATURES_4 = https://gis.qldc.govt.nz/portal   # Portal URL

Writers:
- ARCGISPORTALFEATURES_3: ARCGISPORTALFEATURES to $(DestDataset_ARCGISPORTALFEATURES) in NZTM
- ARCGISPORTALFEATURES_1: ARCGISPORTALFEATURES to $(DestDataset_ARCGISPORTALFEATURES_5)
- ARCGISPORTALFEATURES_2: ARCGISPORTALFEATURES to $(DestDataset_ARCGISPORTALFEATURES_4) in NZTM

Bookmark: datetime
Creator
    GEOMTYPE = Geometry Object
    NUM = 1
    CREATED -> DateTimeStamper
DateTimeStamper
    DATETIME_ATTR = origin_utc
    INCLUDE_FRAC_SECONDS = YES
    INCLUDE_OFFSET = NO
    STAMP_TYPE = datetime
    TIMEZONE = utc
    -> AttributeCreator
AttributeCreator
    ATTR_TABLE = SET_TO origin_utc (buffer) = @int(@Value(origin_utc))
    -> Junction_9
Junction_9
    -> Junction_10

Bookmark: extract: mid/mif files
Junction_10
    -> FeatureReader [INITIATOR]
FeatureReader
    ATTRIBUTES =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
    ATTR_ACCUM_MODE = Merge Initiator and Result
    ATTR_CONFLICT_RES = Use Result
    ATTR_IGNORE_NULLS = No
    COMBINE_GEOM = Use Result
    DATASET = $(FME_MF_DIR_ENCODED)imports\iam_network\wastewater\MIF\*.MIF
    FEATURETYPES = CCTV survey Pipe
    FORMAT = MIF
    INTERACT = NONE
    MIF_ENCODED_ATTRS = mif_text_string
    MIF_ENCODED_ATTR_NAMES = YES
    MIF_ENCODING = fme-source-encoding
    MIF_PRESERVE_DUPLICATES = YES
    MIF_UNENCODED_ATTR_PREFIX = fme_ mif_
    MIF_USE_SEARCH_ENVELOPE = NO
    ORDER_RESULTS = No
    OUTPUT_FEATURES_DISPLAY = Schema and Data Features
    CCTV survey -> Junction_3
    Pipe -> Junction_5
    <REJECTED> -> FeatureReader__Rejected_
Junction_5
    -> Junction_6
Junction_3
    -> Junction_4
FeatureReader__Rejected_: Logger
    LOG_FEATURE = LOG_ONLY
    MAXCOORDS = 20
    MAXFEATS = 20
    MESSAGE = Feature is:
    SEVERITY = INFO

Bookmark: transform: data
Junction_6
    -> GeometryExtractor_2
GeometryExtractor_2
    ATTR = _geometry
    KIND_LONG = OGC Well Known Text
    OGCVERSION = 1.2
    OGC_WKT_PRECISION_DISPLAY = 64-bit
    REMOVE_GEOMETRY = No
    -> BulkAttributeRemover
    <REJECTED> -> GeometryExtractor_2_Output
BulkAttributeRemover
    ATTR_EXP = ^user_
    -> AttributeManager_2
AttributeManager_2
    ATTR_TABLE:
      REMOVE _creation_instance (uint64)
      REMOVE _geometry (buffer)
    -> DateTimeConverter_2
DateTimeConverter_2
    DATETIME_ATTR = survey_date year_laid year_renew
    IN_FORMAT = %N/%e/%Y
    OUT_FORMAT = %Y%m%d
    PASSTHROUGH = NO
    REPAIR_INPUT = YES
    -> AttributeManager_4
    <REJECTED> -> AttributeManager_4
AttributeManager_4
    ATTR_TABLE:
      RENAME_SET_VALUE length > conduit_length (real64)
      RENAME_SET_VALUE shape > conduit_shape (varchar(10))
    -> Junction_11
Junction_11
    -> Junction_12
GeometryExtractor_2_Output: Logger
    LOG_FEATURE = LOG_ONLY
    MAXCOORDS = 20
    MAXFEATS = 20
    MESSAGE = Feature is:
    SEVERITY = INFO
Junction_4
    -> GeometryExtractor
GeometryExtractor
    ATTR = _geometry
    KIND_LONG = OGC Well Known Text
    OGCVERSION = 1.2
    OGC_WKT_PRECISION_DISPLAY = 64-bit
    REMOVE_GEOMETRY = No
    -> AttributeManager
    <REJECTED> -> GeometryExtractor__Rejected_
AttributeManager
    ATTR_TABLE:
      REMOVE _creation_instance (uint64)
      SET_TO splitsurvey (logical) = FME_CONDITIONAL:DEFAULT_VALUE'T'BOOL_OP;OR;COMPOSITE_TEST;1;TEST @Value(splitsurvey) = ?'F'FME_NUM_CONDITIONS2___
      SET_TO splitsurveyref (varchar(40)) = FME_CONDITIONAL:DEFAULT_VALUE'FME_NULL_VALUE'BOOL_OP;OR;COMPOSITE_TEST;1;TEST splitsurveyref ATTRIBUTE_HAS_A_VALUE _FME_BLANK_STRING_'@Value(splitsurveyref)'FME_NUM_CONDITIONS2___
      REMOVE surveyed_by (varchar(25))
      REMOVE actual_cost (real64)
      REMOVE actual_duration (real64)
      REMOVE catchment (varchar(30))
      REMOVE category_code (varchar(3))
      REMOVE CH2MHill_grade (varchar(2))
      REMOVE CH2MHill_maint_grade (varchar(2))
      REMOVE CH2MHill_maint_score (real64)
      REMOVE CH2MHill_score (real64)
      REMOVE CH2MHill_struct_grade (varchar(2))
      REMOVE CH2MHill_struct_score (real64)
      REMOVE comments (varchar(255))
      REMOVE completed (logical)
      REMOVE contract_no (varchar(100))
      REMOVE contractor (varchar(32))
      REMOVE customer (varchar(40))
      REMOVE date_cleaned (varchar(64))
      REMOVE date_completed (varchar(64))
      REMOVE date_planned (varchar(64))
      REMOVE date_started (datetime)
      REMOVE district (varchar(200))
      REMOVE division (varchar(255))
      REMOVE estimated_completion_date (varchar(64))
      REMOVE estimated_cost (real64)
      REMOVE estimated_duration (real64)
      REMOVE finish_cover (real64)
      REMOVE finish_depth (real64)
      REMOVE finish_invert (real64)
      REMOVE flow_control (varchar(25))
      REMOVE gas_detected (logical)
      REMOVE grade_to_invert_D (real64)
      REMOVE grade_to_invert_U (real64)
      REMOVE index (int32)
      REMOVE job_number (varchar(15))
      REMOVE lining (varchar(10))
      REMOVE lining_type (varchar(30))
      REMOVE location (varchar(100))
      REMOVE location_details (varchar(255))
      REMOVE location_photo (varchar(50))
      REMOVE location_photo_ref (varchar(30))
      REMOVE location_sketch (varchar(50))
      REMOVE location_sketch_ref (varchar(30))
      REMOVE long_location (real64)
      REMOVE material (varchar(64))
      REMOVE owner (varchar(64))
      REMOVE pacp_oandm_index_rating (real64)
      REMOVE pacp_oandm_quick_rating (varchar(6))
      REMOVE pacp_oandm_rating (int32)
      REMOVE pacp_overall_index_rating (real64)
      REMOVE pacp_overall_quick_rating (varchar(6))
      REMOVE pacp_overall_rating (int32)
      REMOVE pacp_struct_index_rating (real64)
      REMOVE pacp_struct_quick_rating (varchar(6))
      REMOVE pacp_struct_rating (int32)
      REMOVE photo_reference (varchar(200))
      REMOVE photo_storage (varchar(1))
      REMOVE pipe_unit_length (real64)
      REMOVE place_name (varchar(64))
      REMOVE preclean (logical)
      REMOVE preclean_choice (varchar(15))
      REMOVE purpose (varchar(64))
      REMOVE repeat_period (varchar(20))
      REMOVE repeat_schedule_number (varchar(40))
      REMOVE reverse_setup (int32)
      REMOVE rim_to_invert_D (real64)
      REMOVE rim_to_invert_U (real64)
      REMOVE road_name (varchar(64))
      REMOVE schedule_number (varchar(40))
      REMOVE shape (varchar(15))
      REMOVE sheet_number (int32)
      REMOVE size_1 (real64)
      REMOVE size_2 (real64)
      REMOVE start_cover (real64)
      REMOVE start_depth (real64)
      REMOVE start_invert (real64)
      REMOVE strategic (varchar(30))
      REMOVE team_leader (varchar(40))
      REMOVE temperature (varchar(3))
      REMOVE use (varchar(15))
      REMOVE video_file_in (varchar(255))
      REMOVE video_recorder (varchar(255))
      REMOVE vt_no (varchar(5))
      REMOVE weather (varchar(12))
      REMOVE year_laid (varchar(9))
      REMOVE year_renewed (int32)
      REMOVE _geometry (buffer)
    -> DateTimeConverter
DateTimeConverter
    DATETIME_ATTR = when_surveyed
    IN_FORMAT = %N/%e/%Y
    OUT_FORMAT = %Y%m%d%H%M%S
    PASSTHROUGH = NO
    REPAIR_INPUT = YES
    -> Junction
    <REJECTED> -> Junction
Junction
    -> Junction_2
GeometryExtractor__Rejected_: Logger
    LOG_FEATURE = LOG_ONLY
    MAXCOORDS = 20
    MAXFEATS = 20
    MESSAGE = Feature is:
    SEVERITY = INFO

Bookmark: load: 2 agol
Junction_12
    -> pipe (writer ARCGISPORTALFEATURES_2)
pipe (writer ARCGISPORTALFEATURES_2)
    attributes: link_id String(32), access_restrictions String(64), asset_id String(40), backdrop_diam Double, branch_id Integer, capacity Double, condition_code String(8), condition_score Integer, consequence_comments String(255), consequence_score Double, criticality String(5), current_value Double, date_cleaned String(64), drainage_code String(10), ds_depth_from_cover Double, ds_height Double, ds_image_filename String(255), ds_image_ref String(30), ds_invert Double, ds_lining_material String(10), ds_lining_type String(10), ds_node_id String(40), ds_pipe_material String(64), ds_shape String(10), ds_width Double, flow_control String(10), gradient Double, ground_type String(64), ground_water_risk Double, height Double,
      inspection_cost Double, install_cost Double, int_pipe_CH2MHill_maint_scr Integer, int_pipe_CH2MHill_scr Integer, int_pipe_CH2MHill_struc_scr Integer, internal_pipe_score Integer, conduit_length Double, lifetime Integer, likelihood_score Double, lining_material String(10), lining_type String(10), link_suffix String(1), location String(100), mobile_uid String(100), odour_nuisance_risk Double, owner String(64), pipe_class String(64), pipe_material String(64), pipe_type String(10), property_flooding_risk Double, rail_business_disruption_risk Double, rehab_cost Double, repair_cost Double, repair_cost_risk Double, replace_cost Double, risk_score Double, security String(10), service_condition_score Integer, conduit_shape String(10), site_condition String(10),
      status String(10), surface_water_risk Double, survey_date String(64), system_type String(10), taking_off_reference String(2), traffic_delay_risk Double, traffic_level Double, uid String(32), unit_length Double, us_depth_from_cover Double, us_image_filename String(255), us_image_ref String(30), us_invert Double, us_node_id String(40), width Double, year_laid String(64), year_renew String(64), origin_utc Date
Junction_2
    -> cctv_survey (writer ARCGISPORTALFEATURES_3)
cctv_survey (writer ARCGISPORTALFEATURES_3)
    attributes: id String, uid String, start_manhole String, finish_manhole String, direction String, splitsurvey String, splitsurveyref String, current String, us_node_id String, ds_node_id String, link_suffix String, standard String, orig_coding String, hard_wired_service_grade Double, hard_wired_structural_grade Double, mean_score Double, method String, peak_score Double, pipe_length Double, plr String, service_mean_score Double, service_override_grade Double, service_peak_score Double, service_total_score Double, structural_override_grade Double, structural_rating Double, surveyed_length Double, total_length Double, total_score Double, video_image_loc String,
      when_surveyed Date, origin_utc Date
