FME workspace A stormwater - import gis.fmw

Parameters:
- dir = $(FME_MF_DIR)exports\stormwater   # Folder

Bookmark: datetime
Creator
    GEOMTYPE = Geometry Object
    NUM = 1
    CREATED -> DateTimeStamper
DateTimeStamper
    DATETIME_ATTR = origin_utc
    INCLUDE_FRAC_SECONDS = NO
    INCLUDE_OFFSET = NO
    STAMP_TYPE = datetime
    TIMEZONE = utc
    -> Junction
    -> Junction_21
    -> Junction_23
    -> Junction_25
Junction_21
    -> Junction_22
Junction
    -> Junction_2
Junction_23
    -> Junction_24
Junction_25
    -> Junction_26

Bookmark: extract: three watersdata from AGOL for the wastewater network
Junction_22
    -> polygons [INITIATOR]
polygons: FeatureReader
    ARCGISONLINEFEATURES_CREATE_FEATURE_TABLES_FROM_DATA = Yes
    ARCGISONLINEFEATURES_FEATURESERVICE = Queenstown Lakes District Council Open Data/Three Waters Assets(a99d1860d32f44fbb025142a364d0458)
    ARCGISONLINEFEATURES_FEATURES_PER_REQUEST = 1000
    ARCGISONLINEFEATURES_FORMAT_GUID = YES
    ARCGISONLINEFEATURES_NC = hywell Esri ArcGIS Online
    ARCGISONLINEFEATURES_QUERY_FEATURE_TYPES_FOR_MERGE_FILTERS = Yes
    ARCGISONLINEFEATURES_RESOLVE_DOMAINS = No
    ARCGISONLINEFEATURES_USE_SEARCH_ENVELOPE = NO
    ATTRIBUTES = "Stormwater Channel","OBJECTID,COMPKEY,ASSETTYPE,DESCR,SERVSTAT,OWN,CONMATL,LENGTH,TPWIDTH,BSWIDTH,CHDEPTH,CHANSHAPE,UPNODE,UPSELEV,DWNNODE,DWNELEV,INSTDATE,ASBUILT,SCHEME,DATA_SRC,COMMENTS,ADDDBY,ADDDTTM,MODBY,MODDTTM,CONFIDENCE,CRITICALITY,GlobalID,created_user,created_date,last_edited_user,last_edited_date,Shape__Length","Stormwater Inlet","OBJECTID,COMPKEY,ASSETTYPE,DESCR,SERVSTAT,OWN,ZCOORD,INVERTELEV,CVRTYPE,MANUFCT,INSTDATE,ASBUILT,SCHEME,DATA_SRC,COMMENTS,ADDDBY,ADDDTTM,MODBY,MODDTTM,CONFIDENCE,CRITICALITY,GlobalID,created_user,created_date,last_edited_user,last_edited_date","Stormwater Lateral","OBJECTID,COMPKEY,ASSETTYPE,SRVTYPE,DESCR,SERVSTAT,OWN,PIPEMATL,PIPELEN,NOMDIAM,INTDIAM,OUTDIAM,UPNODE,UPSELEV,DWNNODE,DWNELEV,CLASS,JTTYPE,MANUFCT,INSTDATE,ASBUILT,SCHEME,DATA_SRC,COMMENTS,ADDDBY,ADDDTTM,MODBY,MODDTTM,CONFIDENCE,CRITICALITY,GlobalID,created_user,created_date,last_edited_user,last_edited_date,Shape__Length","Stormwater Main","OBJECTID,COMPKEY,ASSETTYPE,DESCR,SERVSTAT,OWN,PIPEMATL,PIPELEN,NOMDIAM,INTDIAM,OUTDIAM,UPNODE,UPSELEV,DWNNODE,DWNELEV,CLASS,JTTYPE,MANUFCT,INSTMTHD,INSTDATE,LINEMATL,LINEDATE,LINEMTHD,ASBUILT,SCHEME,DATA_SRC,COMMENTS,ADDDBY,ADDDTTM,MODBY,MODDTTM,CONFIDENCE,CRITICALITY,GlobalID,created_user,created_date,last_edited_user,last_edited_date,Shape__Length","Stormwater Manhole","OBJECTID,COMPKEY,ASSETTYPE,DESCR,SERVSTAT,OWN,ZCOORD,INVERTELEV,BARLSHAPE,BARLDIAM,BARLDIM2,CHAMATL,CVRDIAM,CVRTYPE,MANUFCT,INSTDATE,ASBUILT,SCHEME,DATA_SRC,COMMENTS,ADDDBY,ADDDTTM,MODBY,MODDTTM,CONFIDENCE,CRITICALITY,GlobalID,created_user,created_date,last_edited_user,last_edited_date","Stormwater Meter","OBJECTID,COMPKEY,ASSETTYPE,DESCR,SERVSTAT,OWN,ZCOORD,INVERTELEV,METERSZ,SERNO,MODELNO,INSTDATE,ASBUILT,SCHEME,DATA_SRC,COMMENTS,ADDDBY,ADDDTTM,MODBY,MODDTTM,CONFIDENCE,CRITICALITY,GlobalID,created_user,created_date,last_edited_user,last_edited_date","Stormwater Node","OBJECTID,COMPKEY,ASSETTYPE,DESCR,SERVSTAT,OWN,ZCOORD,INVERTELEV,INSTDATE,ASBUILT,SCHEME,DATA_SRC,COMMENTS,ADDDBY,ADDDTTM,MODBY,MODDTTM,CONFIDENCE,CRITICALITY,GlobalID,created_user,created_date,last_edited_user,last_edited_date","Stormwater Pumpstation","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,GlobalID,created_user,created_date,last_edited_user,last_edited_date,Shape__Area,Shape__Length","Stormwater Structure","OBJECTID,COMPKEY,ASSETTYPE,DESCR,SERVSTAT,OWN,ZCOORD,MANUFCT,INSTDATE,ASBUILT,SCHEME,DATA_SRC,COMMENTS,ADDDBY,ADDDTTM,MODBY,MODDTTM,CONFIDENCE,CRITICALITY,GlobalID,created_user,created_date,last_edited_user,last_edited_date","Stormwater Treatment Device","OBJECTID,COMPKEY,ASSETTYPE,DESCR,SERVSTAT,OWN,ZCOORD,INVERTELEV,DEVCAREA,BARLDIAM,BARLDIM2,DVCMATL,CVRDIAM,CVRTYPE,MANUFCT,INSTDATE,ASBUILT,SCHEME,DATA_SRC,COMMENTS,ADDDBY,ADDDTTM,MODBY,MODDTTM,CONFIDENCE,CRITICALITY,GlobalID,created_user,created_date,last_edited_user,last_edited_date,VOIDMAT","Stormwater Treatment Device Area","OBJECTID,COMPKEYREF,COMMENTS,ADDDBY,ADDDTTM,MODBY,MODDTTM,GlobalID,created_user,created_date,last_edited_user,last_edited_date,Shape__Area,Shape__Length","Stormwater Valve","OBJECTID,COMPKEY,ASSETTYPE,DESCR,SERVSTAT,OWN,ZCOORD,INVERTELEV,VALVESTAT,VALVESZ,SERNO,MODELNO,MANUFCT,INSTDATE,ASBUILT,SCHEME,DATA_SRC,COMMENTS,ADDDBY,ADDDTTM,MODBY,MODDTTM,CONFIDENCE,CRITICALITY,GlobalID,created_user,created_date,last_edited_user,last_edited_date","Wastewater Lateral","OBJECTID,COMPKEY,ASSETTYPE,SRVTYPE,DESCR,SERVSTAT,OWN,PIPEMATL,PIPELEN,NOMDIAM,INTDIAM,OUTDIAM,CLASS,MANUFCT,INSTDATE,ASBUILT,SCHEME,DATA_SRC,COMMENTS,ADDDBY,ADDDTTM,MODBY,MODDTTM,CONFIDENCE,CRITICALITY,GlobalID,created_user,created_date,last_edited_user,last_edited_date,Shape__Length","Wastewater Main","OBJECTID,COMPKEY,ASSETTYPE,DESCR,SERVSTAT,OWN,PIPEMATL,PIPELEN,NOMDIAM,INTDIAM,OUTDIAM,UPNODE,UPSELEV,DWNNODE,DWNELEV,CLASS,INSTDATE,JTTYPE,MANUFCT,INSTMTHD,LINEMATL,LINEMTHD,LINEDATE,ASBUILT,SCHEME,DATA_SRC,COMMENTS,ADDDBY,ADDDTTM,MODBY,MODDTTM,CONFIDENCE,CRITICALITY,GlobalID,created_user,created_date,last_edited_user,last_edited_date,Shape__Length","Wastewater Manhole","OBJECTID,COMPKEY,ASSETTYPE,SUBTYPE,DESCR,SERVSTAT,OWN,ZCOORD,INVERTELEV,BARLSHAPE,BARLDIAM,BARLDIM2,CHAMATL,CVRTYPE,CVRDIAM,MANUFCT,INSTDATE,ASBUILT,SCHEME,DATA_SRC,COMMENTS,ADDDBY,ADDDTTM,MODBY,MODDTTM,CONFIDENCE,CRITICALITY,GlobalID,created_user,created_date,last_edited_user,last_edited_date","Wastewater Meter","OBJECTID,COMPKEY,ASSETTYPE,DESCR,SERVSTAT,OWN,ZCOORD,INVERTELEV,METERSZ,SERNO,MODELNO,MANUFCT,INSTDATE,ASBUILT,SCHEME,DATA_SRC,COMMENTS,ADDDBY,ADDDTTM,MODBY,MODDTTM,CONFIDENCE,CRITICALITY,GlobalID,created_user,created_date,last_edited_user,last_edited_date","Wastewater Node","OBJECTID,COMPKEY,ASSETTYPE,DESCR,SERVSTAT,OWN,ZCOORD,INVERTELEV,INSTDATE,ASBUILT,SCHEME,DATA_SRC,COMMENTS,ADDDBY,ADDDTTM,MODBY,MODDTTM,CONFIDENCE,CRITICALITY,GlobalID,created_user,created_date,last_edited_user,last_edited_date","Wastewater Pumpstation","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,created_user,created_date,last_edited_user,last_edited_date,GlobalID,Shape__Area,Shape__Length","Wastewater Treatment Plant","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,created_user,created_date,last_edited_user,last_edited_date,GlobalID,Shape__Area,Shape__Length","Wastewater Valve","OBJECTID,COMPKEY,ASSETTYPE,DESCR,SERVSTAT,OWN,ZCOORD,INVERTELEV,VALVESTAT,VALVESZ,SERNO,MODELNO,MANUFCT,INSTDATE,ASBUILT,SCHEME,DATA_SRC,COMMENTS,ADDDBY,ADDDTTM,MODBY,MODDTTM,CONFIDENCE,CRITICALITY,GlobalID,created_user,created_date,last_edited_user,last_edited_date","Water Supply Backflow","OBJECTID,COMPKEY,ASSETTYPE,DESCR,SERVSTAT,OWN,ZCOORD,INVERTELEV,VALVESTAT,VALVESZ,SERNO,MODELNO,MANUFCT,INSTDATE,ASBUILT,SCHEME,DATA_SRC,COMMENTS,ADDDBY,ADDDTTM,MODBY,MODDTTM,CONFIDENCE,CRITICALITY,GlobalID,created_user,created_date,last_edited_user,last_edited_date","Water Supply Hydrant","OBJECTID,COMPKEY,ASSETTYPE,DESCR,SERVSTAT,OWN,ZCOORD,INVERTELEV,MODELNO,MANUFCT,INSTDATE,ASBUILT,SCHEME,DATA_SRC,COMMENTS,ADDDBY,ADDDTTM,MODBY,MODDTTM,CONFIDENCE,CRITICALITY,GlobalID,created_user,created_date,last_edited_user,last_edited_date","Water Supply Lateral","OBJECTID,COMPKEY,ASSETTYPE,SRVTYPE,DESCR,SERVSTAT,OWN,PIPEMATL,PIPELEN,NOMDIAM,INTDIAM,OUTDIAM,CLASS,MANUFCT,INSTDATE,ASBUILT,SCHEME,DATA_SRC,COMMENTS,ADDDBY,ADDDTTM,MODBY,MODDTTM,CONFIDENCE,CRITICALITY,GlobalID,created_user,created_date,last_edited_user,last_edited_date,Shape__Length","Water Supply Main","OBJECTID,COMPKEY,ASSETTYPE,DESCR,SERVSTAT,OWN,PIPEMATL,PIPELEN,NOMDIAM,INTDIAM,OUTDIAM,DPTH,UPNODE,DWNNODE,CLASS,INSTDATE,JTTYPE,MANUFCT,INSTMTHD,LINEMATL,LINEMTHD,LINEDATE,ASBUILT,SCHEME,DATA_SRC,COMMENTS,ADDDBY,ADDDTTM,MODBY,MODDTTM,CONFIDENCE,CRITICALITY,GlobalID,created_user,created_date,last_edited_user,last_edited_date,Shape__Length","Water Supply Meter","OBJECTID,COMPKEY,ASSETTYPE,DESCR,SERVSTAT,OWN,ZCOORD,INVERTELEV,METERSZ,SERNO,MODELNO,MANUFCT,INSTDATE,ASBUILT,SCHEME,DATA_SRC,COMMENTS,ADDDBY,ADDDTTM,MODBY,MODDTTM,CONFIDENCE,CRITICALITY,GlobalID,created_user,created_date,last_edited_user,last_edited_date","Water Supply Miscellaneous","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,GlobalID,created_user,created_date,last_edited_user,last_edited_date,Shape__Area,Shape__Length","Water Supply Node","OBJECTID,COMPKEY,ASSETTYPE,DESCR,SERVSTAT,OWN,ZCOORD,INVERTELEV,INSTDATE,ASBUILT,SCHEME,DATA_SRC,COMMENTS,ADDDBY,ADDDTTM,MODBY,MODDTTM,CONFIDENCE,CRITICALITY,GlobalID,created_user,created_date,last_edited_user,last_edited_date","Water Supply Pressure Zones","OBJECTID,Id,Zone_Name,Name_Code,Rated_Cons,GlobalID,created_user,created_date,last_edited_user,last_edited_date,Shape__Area,Shape__Length","Water Supply Pumpstation","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,created_user,created_date,last_edited_user,last_edited_date,GlobalID,Shape__Area,Shape__Length","Water Supply Reservoir","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,created_user,created_date,last_edited_user,last_edited_date,GlobalID,Shape__Area,Shape__Length","Water Supply Treatment Plant","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,created_user,created_date,last_edited_user,last_edited_date,GlobalID,Shape__Area,Shape__Length","Water Supply Valve","OBJECTID,COMPKEY,ASSETTYPE,DESCR,SERVSTAT,OWN,ZCOORD,INVERTELEV,VALVESTAT,VALVESZ,SERNO,MODELNO,MANUFCT,INSTDATE,ASBUILT,SCHEME,DATA_SRC,COMMENTS,ADDDBY,ADDDTTM,MODBY,MODDTTM,CONFIDENCE,CRITICALITY,GlobalID,created_user,created_date,last_edited_user,last_edited_date"
    ATTR_ACCUM_MODE = Merge Initiator and Result
    ATTR_CONFLICT_RES = Use Result
    ATTR_IGNORE_NULLS = No
    COMBINE_GEOM = Use Result
    FEATURETYPES = Stormwater Pumpstation Stormwater Treatment Device Area
    FORMAT = ARCGISONLINEFEATURES
    INTERACT = NONE
    ORDER_RESULTS = No
    OUTPUT_FEATURES_DISPLAY = Schema and Data Features
    Stormwater Pumpstation -> Junction_11
    Stormwater Treatment Device Area -> AttributeCreator_4
Junction_11
    -> Junction_12
AttributeCreator_4
    ATTR_TABLE = SET_TO COMPKEY (buffer) = FME_NULL_VALUE
    -> Junction_13
Junction_13
    -> Junction_14
Junction_2
    -> schemes [INITIATOR]
schemes: FeatureReader
    ARCGISONLINEFEATURES_CREATE_FEATURE_TABLES_FROM_DATA = Yes
    ARCGISONLINEFEATURES_FEATURESERVICE = Queenstown Lakes District Council Open Data/Three Waters Schemes(c2b563e7c41f44a6ad5d04efd337d118)
    ARCGISONLINEFEATURES_FEATURES_PER_REQUEST = 1000
    ARCGISONLINEFEATURES_FORMAT_GUID = YES
    ARCGISONLINEFEATURES_NC = hywell Esri ArcGIS Online
    ARCGISONLINEFEATURES_QUERY_FEATURE_TYPES_FOR_MERGE_FILTERS = Yes
    ARCGISONLINEFEATURES_RESOLVE_DOMAINS = No
    ARCGISONLINEFEATURES_USE_SEARCH_ENVELOPE = NO
    ATTRIBUTES = "Scheme Boundaries","OBJECTID,WaterType,Name,Ownership,Delivery,Maintenance,DecisionDate,VolumeRestrictions,Notes,GlobalID,created_user,created_date,last_edited_user,last_edited_date,Shape__Area,Shape__Length"
    ATTR_ACCUM_MODE = Merge Initiator and Result
    ATTR_CONFLICT_RES = Use Result
    ATTR_IGNORE_NULLS = No
    COMBINE_GEOM = Use Result
    FEATURETYPES = Scheme Boundaries
    FORMAT = ARCGISONLINEFEATURES
    INTERACT = NONE
    ORDER_RESULTS = No
    OUTPUT_FEATURES_DISPLAY = Schema and Data Features
    WHERE = "WaterType"=3
    Scheme Boundaries -> Junction_17
Junction_17
    -> Junction_18
Junction_24
    -> polylines [INITIATOR]
polylines: FeatureReader
    ARCGISONLINEFEATURES_CREATE_FEATURE_TABLES_FROM_DATA = Yes
    ARCGISONLINEFEATURES_FEATURESERVICE = Queenstown Lakes District Council Open Data/Three Waters Assets(a99d1860d32f44fbb025142a364d0458)
    ARCGISONLINEFEATURES_FEATURES_PER_REQUEST = 1000
    ARCGISONLINEFEATURES_FORMAT_GUID = YES
    ARCGISONLINEFEATURES_NC = hywell Esri ArcGIS Online
    ARCGISONLINEFEATURES_QUERY_FEATURE_TYPES_FOR_MERGE_FILTERS = Yes
    ARCGISONLINEFEATURES_RESOLVE_DOMAINS = No
    ARCGISONLINEFEATURES_USE_SEARCH_ENVELOPE = NO
    ATTRIBUTES = "Stormwater Channel","OBJECTID,COMPKEY,ASSETTYPE,DESCR,SERVSTAT,OWN,CONMATL,LENGTH,TPWIDTH,BSWIDTH,CHDEPTH,CHANSHAPE,UPNODE,UPSELEV,DWNNODE,DWNELEV,INSTDATE,ASBUILT,SCHEME,DATA_SRC,COMMENTS,ADDDBY,ADDDTTM,MODBY,MODDTTM,CONFIDENCE,CRITICALITY,GlobalID,created_user,created_date,last_edited_user,last_edited_date,Shape__Length","Stormwater Inlet","OBJECTID,COMPKEY,ASSETTYPE,DESCR,SERVSTAT,OWN,ZCOORD,INVERTELEV,CVRTYPE,MANUFCT,INSTDATE,ASBUILT,SCHEME,DATA_SRC,COMMENTS,ADDDBY,ADDDTTM,MODBY,MODDTTM,CONFIDENCE,CRITICALITY,GlobalID,created_user,created_date,last_edited_user,last_edited_date","Stormwater Lateral","OBJECTID,COMPKEY,ASSETTYPE,SRVTYPE,DESCR,SERVSTAT,OWN,PIPEMATL,PIPELEN,NOMDIAM,INTDIAM,OUTDIAM,UPNODE,UPSELEV,DWNNODE,DWNELEV,CLASS,JTTYPE,MANUFCT,INSTDATE,ASBUILT,SCHEME,DATA_SRC,COMMENTS,ADDDBY,ADDDTTM,MODBY,MODDTTM,CONFIDENCE,CRITICALITY,GlobalID,created_user,created_date,last_edited_user,last_edited_date,Shape__Length","Stormwater Main","OBJECTID,COMPKEY,ASSETTYPE,DESCR,SERVSTAT,OWN,PIPEMATL,PIPELEN,NOMDIAM,INTDIAM,OUTDIAM,UPNODE,UPSELEV,DWNNODE,DWNELEV,CLASS,JTTYPE,MANUFCT,INSTMTHD,INSTDATE,LINEMATL,LINEDATE,LINEMTHD,ASBUILT,SCHEME,DATA_SRC,COMMENTS,ADDDBY,ADDDTTM,MODBY,MODDTTM,CONFIDENCE,CRITICALITY,GlobalID,created_user,created_date,last_edited_user,last_edited_date,Shape__Length","Stormwater Manhole","OBJECTID,COMPKEY,ASSETTYPE,DESCR,SERVSTAT,OWN,ZCOORD,INVERTELEV,BARLSHAPE,BARLDIAM,BARLDIM2,CHAMATL,CVRDIAM,CVRTYPE,MANUFCT,INSTDATE,ASBUILT,SCHEME,DATA_SRC,COMMENTS,ADDDBY,ADDDTTM,MODBY,MODDTTM,CONFIDENCE,CRITICALITY,GlobalID,created_user,created_date,last_edited_user,last_edited_date","Stormwater Meter","OBJECTID,COMPKEY,ASSETTYPE,DESCR,SERVSTAT,OWN,ZCOORD,INVERTELEV,METERSZ,SERNO,MODELNO,INSTDATE,ASBUILT,SCHEME,DATA_SRC,COMMENTS,ADDDBY,ADDDTTM,MODBY,MODDTTM,CONFIDENCE,CRITICALITY,GlobalID,created_user,created_date,last_edited_user,last_edited_date","Stormwater Node","OBJECTID,COMPKEY,ASSETTYPE,DESCR,SERVSTAT,OWN,ZCOORD,INVERTELEV,INSTDATE,ASBUILT,SCHEME,DATA_SRC,COMMENTS,ADDDBY,ADDDTTM,MODBY,MODDTTM,CONFIDENCE,CRITICALITY,GlobalID,created_user,created_date,last_edited_user,last_edited_date","Stormwater Pumpstation","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,GlobalID,created_user,created_date,last_edited_user,last_edited_date,Shape__Area,Shape__Length","Stormwater Structure","OBJECTID,COMPKEY,ASSETTYPE,DESCR,SERVSTAT,OWN,ZCOORD,MANUFCT,INSTDATE,ASBUILT,SCHEME,DATA_SRC,COMMENTS,ADDDBY,ADDDTTM,MODBY,MODDTTM,CONFIDENCE,CRITICALITY,GlobalID,created_user,created_date,last_edited_user,last_edited_date","Stormwater Treatment Device","OBJECTID,COMPKEY,ASSETTYPE,DESCR,SERVSTAT,OWN,ZCOORD,INVERTELEV,DEVCAREA,BARLDIAM,BARLDIM2,DVCMATL,CVRDIAM,CVRTYPE,MANUFCT,INSTDATE,ASBUILT,SCHEME,DATA_SRC,COMMENTS,ADDDBY,ADDDTTM,MODBY,MODDTTM,CONFIDENCE,CRITICALITY,GlobalID,created_user,created_date,last_edited_user,last_edited_date,VOIDMAT","Stormwater Treatment Device Area","OBJECTID,COMPKEYREF,COMMENTS,ADDDBY,ADDDTTM,MODBY,MODDTTM,GlobalID,created_user,created_date,last_edited_user,last_edited_date,Shape__Area,Shape__Length","Stormwater Valve","OBJECTID,COMPKEY,ASSETTYPE,DESCR,SERVSTAT,OWN,ZCOORD,INVERTELEV,VALVESTAT,VALVESZ,SERNO,MODELNO,MANUFCT,INSTDATE,ASBUILT,SCHEME,DATA_SRC,COMMENTS,ADDDBY,ADDDTTM,MODBY,MODDTTM,CONFIDENCE,CRITICALITY,GlobalID,created_user,created_date,last_edited_user,last_edited_date","Wastewater Lateral","OBJECTID,COMPKEY,ASSETTYPE,SRVTYPE,DESCR,SERVSTAT,OWN,PIPEMATL,PIPELEN,NOMDIAM,INTDIAM,OUTDIAM,CLASS,MANUFCT,INSTDATE,ASBUILT,SCHEME,DATA_SRC,COMMENTS,ADDDBY,ADDDTTM,MODBY,MODDTTM,CONFIDENCE,CRITICALITY,GlobalID,created_user,created_date,last_edited_user,last_edited_date,Shape__Length","Wastewater Main","OBJECTID,COMPKEY,ASSETTYPE,DESCR,SERVSTAT,OWN,PIPEMATL,PIPELEN,NOMDIAM,INTDIAM,OUTDIAM,UPNODE,UPSELEV,DWNNODE,DWNELEV,CLASS,INSTDATE,JTTYPE,MANUFCT,INSTMTHD,LINEMATL,LINEMTHD,LINEDATE,ASBUILT,SCHEME,DATA_SRC,COMMENTS,ADDDBY,ADDDTTM,MODBY,MODDTTM,CONFIDENCE,CRITICALITY,GlobalID,created_user,created_date,last_edited_user,last_edited_date,Shape__Length","Wastewater Manhole","OBJECTID,COMPKEY,ASSETTYPE,SUBTYPE,DESCR,SERVSTAT,OWN,ZCOORD,INVERTELEV,BARLSHAPE,BARLDIAM,BARLDIM2,CHAMATL,CVRTYPE,CVRDIAM,MANUFCT,INSTDATE,ASBUILT,SCHEME,DATA_SRC,COMMENTS,ADDDBY,ADDDTTM,MODBY,MODDTTM,CONFIDENCE,CRITICALITY,GlobalID,created_user,created_date,last_edited_user,last_edited_date","Wastewater Meter","OBJECTID,COMPKEY,ASSETTYPE,DESCR,SERVSTAT,OWN,ZCOORD,INVERTELEV,METERSZ,SERNO,MODELNO,MANUFCT,INSTDATE,ASBUILT,SCHEME,DATA_SRC,COMMENTS,ADDDBY,ADDDTTM,MODBY,MODDTTM,CONFIDENCE,CRITICALITY,GlobalID,created_user,created_date,last_edited_user,last_edited_date","Wastewater Node","OBJECTID,COMPKEY,ASSETTYPE,DESCR,SERVSTAT,OWN,ZCOORD,INVERTELEV,INSTDATE,ASBUILT,SCHEME,DATA_SRC,COMMENTS,ADDDBY,ADDDTTM,MODBY,MODDTTM,CONFIDENCE,CRITICALITY,GlobalID,created_user,created_date,last_edited_user,last_edited_date","Wastewater Pumpstation","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,created_user,created_date,last_edited_user,last_edited_date,GlobalID,Shape__Area,Shape__Length","Wastewater Treatment Plant","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,created_user,created_date,last_edited_user,last_edited_date,GlobalID,Shape__Area,Shape__Length","Wastewater Valve","OBJECTID,COMPKEY,ASSETTYPE,DESCR,SERVSTAT,OWN,ZCOORD,INVERTELEV,VALVESTAT,VALVESZ,SERNO,MODELNO,MANUFCT,INSTDATE,ASBUILT,SCHEME,DATA_SRC,COMMENTS,ADDDBY,ADDDTTM,MODBY,MODDTTM,CONFIDENCE,CRITICALITY,GlobalID,created_user,created_date,last_edited_user,last_edited_date","Water Supply Backflow","OBJECTID,COMPKEY,ASSETTYPE,DESCR,SERVSTAT,OWN,ZCOORD,INVERTELEV,VALVESTAT,VALVESZ,SERNO,MODELNO,MANUFCT,INSTDATE,ASBUILT,SCHEME,DATA_SRC,COMMENTS,ADDDBY,ADDDTTM,MODBY,MODDTTM,CONFIDENCE,CRITICALITY,GlobalID,created_user,created_date,last_edited_user,last_edited_date","Water Supply Hydrant","OBJECTID,COMPKEY,ASSETTYPE,DESCR,SERVSTAT,OWN,ZCOORD,INVERTELEV,MODELNO,MANUFCT,INSTDATE,ASBUILT,SCHEME,DATA_SRC,COMMENTS,ADDDBY,ADDDTTM,MODBY,MODDTTM,CONFIDENCE,CRITICALITY,GlobalID,created_user,created_date,last_edited_user,last_edited_date","Water Supply Lateral","OBJECTID,COMPKEY,ASSETTYPE,SRVTYPE,DESCR,SERVSTAT,OWN,PIPEMATL,PIPELEN,NOMDIAM,INTDIAM,OUTDIAM,CLASS,MANUFCT,INSTDATE,ASBUILT,SCHEME,DATA_SRC,COMMENTS,ADDDBY,ADDDTTM,MODBY,MODDTTM,CONFIDENCE,CRITICALITY,GlobalID,created_user,created_date,last_edited_user,last_edited_date,Shape__Length","Water Supply Main","OBJECTID,COMPKEY,ASSETTYPE,DESCR,SERVSTAT,OWN,PIPEMATL,PIPELEN,NOMDIAM,INTDIAM,OUTDIAM,DPTH,UPNODE,DWNNODE,CLASS,INSTDATE,JTTYPE,MANUFCT,INSTMTHD,LINEMATL,LINEMTHD,LINEDATE,ASBUILT,SCHEME,DATA_SRC,COMMENTS,ADDDBY,ADDDTTM,MODBY,MODDTTM,CONFIDENCE,CRITICALITY,GlobalID,created_user,created_date,last_edited_user,last_edited_date,Shape__Length","Water Supply Meter","OBJECTID,COMPKEY,ASSETTYPE,DESCR,SERVSTAT,OWN,ZCOORD,INVERTELEV,METERSZ,SERNO,MODELNO,MANUFCT,INSTDATE,ASBUILT,SCHEME,DATA_SRC,COMMENTS,ADDDBY,ADDDTTM,MODBY,MODDTTM,CONFIDENCE,CRITICALITY,GlobalID,created_user,created_date,last_edited_user,last_edited_date","Water Supply Miscellaneous","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,GlobalID,created_user,created_date,last_edited_user,last_edited_date,Shape__Area,Shape__Length","Water Supply Node","OBJECTID,COMPKEY,ASSETTYPE,DESCR,SERVSTAT,OWN,ZCOORD,INVERTELEV,INSTDATE,ASBUILT,SCHEME,DATA_SRC,COMMENTS,ADDDBY,ADDDTTM,MODBY,MODDTTM,CONFIDENCE,CRITICALITY,GlobalID,created_user,created_date,last_edited_user,last_edited_date","Water Supply Pressure Zones","OBJECTID,Id,Zone_Name,Name_Code,Rated_Cons,GlobalID,created_user,created_date,last_edited_user,last_edited_date,Shape__Area,Shape__Length","Water Supply Pumpstation","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,created_user,created_date,last_edited_user,last_edited_date,GlobalID,Shape__Area,Shape__Length","Water Supply Reservoir","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,created_user,created_date,last_edited_user,last_edited_date,GlobalID,Shape__Area,Shape__Length","Water Supply Treatment Plant","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,created_user,created_date,last_edited_user,last_edited_date,GlobalID,Shape__Area,Shape__Length","Water Supply Valve","OBJECTID,COMPKEY,ASSETTYPE,DESCR,SERVSTAT,OWN,ZCOORD,INVERTELEV,VALVESTAT,VALVESZ,SERNO,MODELNO,MANUFCT,INSTDATE,ASBUILT,SCHEME,DATA_SRC,COMMENTS,ADDDBY,ADDDTTM,MODBY,MODDTTM,CONFIDENCE,CRITICALITY,GlobalID,created_user,created_date,last_edited_user,last_edited_date"
    ATTR_ACCUM_MODE = Merge Initiator and Result
    ATTR_CONFLICT_RES = Use Result
    ATTR_IGNORE_NULLS = No
    COMBINE_GEOM = Use Result
    FEATURETYPES = Stormwater Channel Stormwater Main Stormwater Lateral
    FORMAT = ARCGISONLINEFEATURES
    INTERACT = NONE
    ORDER_RESULTS = No
    OUTPUT_FEATURES_DISPLAY = Schema and Data Features
    Stormwater Channel -> Junction_4
    Stormwater Main -> Junction_3
    Stormwater Lateral -> Junction_6
Junction_4
    -> Junction_8
Junction_6
    -> Junction_7
Junction_3
    -> Junction_5
Junction_26
    -> nodes [INITIATOR]
nodes: FeatureReader
    ARCGISONLINEFEATURES_ARCGISONLINEFEATURES_EXPOSE_FORMAT_ATTRS = fme_dataset,String(50) fme_feature_type,String(50)
    ARCGISONLINEFEATURES_CREATE_FEATURE_TABLES_FROM_DATA = Yes
    ARCGISONLINEFEATURES_FEATURESERVICE = Queenstown Lakes District Council Open Data/Three Waters Assets(a99d1860d32f44fbb025142a364d0458)
    ARCGISONLINEFEATURES_FEATURES_PER_REQUEST = 1000
    ARCGISONLINEFEATURES_FORMAT_GUID = YES
    ARCGISONLINEFEATURES_NC = hywell Esri ArcGIS Online
    ARCGISONLINEFEATURES_QUERY_FEATURE_TYPES_FOR_MERGE_FILTERS = Yes
    ARCGISONLINEFEATURES_RESOLVE_DOMAINS = No
    ARCGISONLINEFEATURES_USE_SEARCH_ENVELOPE = NO
    ATTRIBUTES = "Stormwater Channel","OBJECTID,COMPKEY,ASSETTYPE,DESCR,SERVSTAT,OWN,CONMATL,LENGTH,TPWIDTH,BSWIDTH,CHDEPTH,CHANSHAPE,UPNODE,UPSELEV,DWNNODE,DWNELEV,INSTDATE,ASBUILT,SCHEME,DATA_SRC,COMMENTS,ADDDBY,ADDDTTM,MODBY,MODDTTM,CONFIDENCE,CRITICALITY,GlobalID,created_user,created_date,last_edited_user,last_edited_date,Shape__Length,fme_dataset,fme_feature_type","Stormwater Inlet","OBJECTID,COMPKEY,ASSETTYPE,DESCR,SERVSTAT,OWN,ZCOORD,INVERTELEV,CVRTYPE,MANUFCT,INSTDATE,ASBUILT,SCHEME,DATA_SRC,COMMENTS,ADDDBY,ADDDTTM,MODBY,MODDTTM,CONFIDENCE,CRITICALITY,GlobalID,created_user,created_date,last_edited_user,last_edited_date,fme_dataset,fme_feature_type","Stormwater Lateral","OBJECTID,COMPKEY,ASSETTYPE,SRVTYPE,DESCR,SERVSTAT,OWN,PIPEMATL,PIPELEN,NOMDIAM,INTDIAM,OUTDIAM,UPNODE,UPSELEV,DWNNODE,DWNELEV,CLASS,JTTYPE,MANUFCT,INSTDATE,ASBUILT,SCHEME,DATA_SRC,COMMENTS,ADDDBY,ADDDTTM,MODBY,MODDTTM,CONFIDENCE,CRITICALITY,GlobalID,created_user,created_date,last_edited_user,last_edited_date,Shape__Length,fme_dataset,fme_feature_type","Stormwater Main","OBJECTID,COMPKEY,ASSETTYPE,DESCR,SERVSTAT,OWN,PIPEMATL,PIPELEN,NOMDIAM,INTDIAM,OUTDIAM,UPNODE,UPSELEV,DWNNODE,DWNELEV,CLASS,JTTYPE,MANUFCT,INSTMTHD,INSTDATE,LINEMATL,LINEDATE,LINEMTHD,ASBUILT,SCHEME,DATA_SRC,COMMENTS,ADDDBY,ADDDTTM,MODBY,MODDTTM,CONFIDENCE,CRITICALITY,GlobalID,created_user,created_date,last_edited_user,last_edited_date,Shape__Length,fme_dataset,fme_feature_type","Stormwater Manhole","OBJECTID,COMPKEY,ASSETTYPE,DESCR,SERVSTAT,OWN,ZCOORD,INVERTELEV,BARLSHAPE,BARLDIAM,BARLDIM2,CHAMATL,CVRDIAM,CVRTYPE,MANUFCT,INSTDATE,ASBUILT,SCHEME,DATA_SRC,COMMENTS,ADDDBY,ADDDTTM,MODBY,MODDTTM,CONFIDENCE,CRITICALITY,GlobalID,created_user,created_date,last_edited_user,last_edited_date,fme_dataset,fme_feature_type","Stormwater Meter","OBJECTID,COMPKEY,ASSETTYPE,DESCR,SERVSTAT,OWN,ZCOORD,INVERTELEV,METERSZ,SERNO,MODELNO,INSTDATE,ASBUILT,SCHEME,DATA_SRC,COMMENTS,ADDDBY,ADDDTTM,MODBY,MODDTTM,CONFIDENCE,CRITICALITY,GlobalID,created_user,created_date,last_edited_user,last_edited_date,fme_dataset,fme_feature_type","Stormwater Node","OBJECTID,COMPKEY,ASSETTYPE,DESCR,SERVSTAT,OWN,ZCOORD,INVERTELEV,INSTDATE,ASBUILT,SCHEME,DATA_SRC,COMMENTS,ADDDBY,ADDDTTM,MODBY,MODDTTM,CONFIDENCE,CRITICALITY,GlobalID,created_user,created_date,last_edited_user,last_edited_date,fme_dataset,fme_feature_type","Stormwater Pumpstation","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,GlobalID,created_user,created_date,last_edited_user,last_edited_date,Shape__Area,Shape__Length,fme_dataset,fme_feature_type","Stormwater Structure","OBJECTID,COMPKEY,ASSETTYPE,DESCR,SERVSTAT,OWN,ZCOORD,MANUFCT,INSTDATE,ASBUILT,SCHEME,DATA_SRC,COMMENTS,ADDDBY,ADDDTTM,MODBY,MODDTTM,CONFIDENCE,CRITICALITY,GlobalID,created_user,created_date,last_edited_user,last_edited_date,fme_dataset,fme_feature_type","Stormwater Treatment Device","OBJECTID,COMPKEY,ASSETTYPE,DESCR,SERVSTAT,OWN,ZCOORD,INVERTELEV,DEVCAREA,BARLDIAM,BARLDIM2,DVCMATL,CVRDIAM,CVRTYPE,MANUFCT,INSTDATE,ASBUILT,SCHEME,DATA_SRC,COMMENTS,ADDDBY,ADDDTTM,MODBY,MODDTTM,CONFIDENCE,CRITICALITY,GlobalID,created_user,created_date,last_edited_user,last_edited_date,VOIDMAT,fme_dataset,fme_feature_type","Stormwater Treatment Device Area","OBJECTID,COMPKEYREF,COMMENTS,ADDDBY,ADDDTTM,MODBY,MODDTTM,GlobalID,created_user,created_date,last_edited_user,last_edited_date,Shape__Area,Shape__Length,fme_dataset,fme_feature_type","Stormwater Valve","OBJECTID,COMPKEY,ASSETTYPE,DESCR,SERVSTAT,OWN,ZCOORD,INVERTELEV,VALVESTAT,VALVESZ,SERNO,MODELNO,MANUFCT,INSTDATE,ASBUILT,SCHEME,DATA_SRC,COMMENTS,ADDDBY,ADDDTTM,MODBY,MODDTTM,CONFIDENCE,CRITICALITY,GlobalID,created_user,created_date,last_edited_user,last_edited_date,fme_dataset,fme_feature_type","Wastewater Lateral","OBJECTID,COMPKEY,ASSETTYPE,SRVTYPE,DESCR,SERVSTAT,OWN,PIPEMATL,PIPELEN,NOMDIAM,INTDIAM,OUTDIAM,CLASS,MANUFCT,INSTDATE,ASBUILT,SCHEME,DATA_SRC,COMMENTS,ADDDBY,ADDDTTM,MODBY,MODDTTM,CONFIDENCE,CRITICALITY,GlobalID,created_user,created_date,last_edited_user,last_edited_date,Shape__Length,fme_dataset,fme_feature_type","Wastewater Main","OBJECTID,COMPKEY,ASSETTYPE,DESCR,SERVSTAT,OWN,PIPEMATL,PIPELEN,NOMDIAM,INTDIAM,OUTDIAM,UPNODE,UPSELEV,DWNNODE,DWNELEV,CLASS,INSTDATE,JTTYPE,MANUFCT,INSTMTHD,LINEMATL,LINEMTHD,LINEDATE,ASBUILT,SCHEME,DATA_SRC,COMMENTS,ADDDBY,ADDDTTM,MODBY,MODDTTM,CONFIDENCE,CRITICALITY,GlobalID,created_user,created_date,last_edited_user,last_edited_date,Shape__Length,fme_dataset,fme_feature_type","Wastewater Manhole","OBJECTID,COMPKEY,ASSETTYPE,SUBTYPE,DESCR,SERVSTAT,OWN,ZCOORD,INVERTELEV,BARLSHAPE,BARLDIAM,BARLDIM2,CHAMATL,CVRTYPE,CVRDIAM,MANUFCT,INSTDATE,ASBUILT,SCHEME,DATA_SRC,COMMENTS,ADDDBY,ADDDTTM,MODBY,MODDTTM,CONFIDENCE,CRITICALITY,GlobalID,created_user,created_date,last_edited_user,last_edited_date,fme_dataset,fme_feature_type","Wastewater Meter","OBJECTID,COMPKEY,ASSETTYPE,DESCR,SERVSTAT,OWN,ZCOORD,INVERTELEV,METERSZ,SERNO,MODELNO,MANUFCT,INSTDATE,ASBUILT,SCHEME,DATA_SRC,COMMENTS,ADDDBY,ADDDTTM,MODBY,MODDTTM,CONFIDENCE,CRITICALITY,GlobalID,created_user,created_date,last_edited_user,last_edited_date,fme_dataset,fme_feature_type","Wastewater Node","OBJECTID,COMPKEY,ASSETTYPE,DESCR,SERVSTAT,OWN,ZCOORD,INVERTELEV,INSTDATE,ASBUILT,SCHEME,DATA_SRC,COMMENTS,ADDDBY,ADDDTTM,MODBY,MODDTTM,CONFIDENCE,CRITICALITY,GlobalID,created_user,created_date,last_edited_user,last_edited_date,fme_dataset,fme_feature_type","Wastewater Pumpstation","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,created_user,created_date,last_edited_user,last_edited_date,GlobalID,Shape__Area,Shape__Length,fme_dataset,fme_feature_type","Wastewater Treatment Plant","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,created_user,created_date,last_edited_user,last_edited_date,GlobalID,Shape__Area,Shape__Length,fme_dataset,fme_feature_type","Wastewater Valve","OBJECTID,COMPKEY,ASSETTYPE,DESCR,SERVSTAT,OWN,ZCOORD,INVERTELEV,VALVESTAT,VALVESZ,SERNO,MODELNO,MANUFCT,INSTDATE,ASBUILT,SCHEME,DATA_SRC,COMMENTS,ADDDBY,ADDDTTM,MODBY,MODDTTM,CONFIDENCE,CRITICALITY,GlobalID,created_user,created_date,last_edited_user,last_edited_date,fme_dataset,fme_feature_type","Water Supply Backflow","OBJECTID,COMPKEY,ASSETTYPE,DESCR,SERVSTAT,OWN,ZCOORD,INVERTELEV,VALVESTAT,VALVESZ,SERNO,MODELNO,MANUFCT,INSTDATE,ASBUILT,SCHEME,DATA_SRC,COMMENTS,ADDDBY,ADDDTTM,MODBY,MODDTTM,CONFIDENCE,CRITICALITY,GlobalID,created_user,created_date,last_edited_user,last_edited_date,fme_dataset,fme_feature_type","Water Supply Hydrant","OBJECTID,COMPKEY,ASSETTYPE,DESCR,SERVSTAT,OWN,ZCOORD,INVERTELEV,MODELNO,MANUFCT,INSTDATE,ASBUILT,SCHEME,DATA_SRC,COMMENTS,ADDDBY,ADDDTTM,MODBY,MODDTTM,CONFIDENCE,CRITICALITY,GlobalID,created_user,created_date,last_edited_user,last_edited_date,fme_dataset,fme_feature_type","Water Supply Lateral","OBJECTID,COMPKEY,ASSETTYPE,SRVTYPE,DESCR,SERVSTAT,OWN,PIPEMATL,PIPELEN,NOMDIAM,INTDIAM,OUTDIAM,CLASS,MANUFCT,INSTDATE,ASBUILT,SCHEME,DATA_SRC,COMMENTS,ADDDBY,ADDDTTM,MODBY,MODDTTM,CONFIDENCE,CRITICALITY,GlobalID,created_user,created_date,last_edited_user,last_edited_date,Shape__Length,fme_dataset,fme_feature_type","Water Supply Main","OBJECTID,COMPKEY,ASSETTYPE,DESCR,SERVSTAT,OWN,PIPEMATL,PIPELEN,NOMDIAM,INTDIAM,OUTDIAM,DPTH,UPNODE,DWNNODE,CLASS,INSTDATE,JTTYPE,MANUFCT,INSTMTHD,LINEMATL,LINEMTHD,LINEDATE,ASBUILT,SCHEME,DATA_SRC,COMMENTS,ADDDBY,ADDDTTM,MODBY,MODDTTM,CONFIDENCE,CRITICALITY,GlobalID,created_user,created_date,last_edited_user,last_edited_date,Shape__Length,fme_dataset,fme_feature_type","Water Supply Meter","OBJECTID,COMPKEY,ASSETTYPE,DESCR,SERVSTAT,OWN,ZCOORD,INVERTELEV,METERSZ,SERNO,MODELNO,MANUFCT,INSTDATE,ASBUILT,SCHEME,DATA_SRC,COMMENTS,ADDDBY,ADDDTTM,MODBY,MODDTTM,CONFIDENCE,CRITICALITY,GlobalID,created_user,created_date,last_edited_user,last_edited_date,fme_dataset,fme_feature_type","Water Supply Miscellaneous","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,GlobalID,created_user,created_date,last_edited_user,last_edited_date,Shape__Area,Shape__Length,fme_dataset,fme_feature_type","Water Supply Node","OBJECTID,COMPKEY,ASSETTYPE,DESCR,SERVSTAT,OWN,ZCOORD,INVERTELEV,INSTDATE,ASBUILT,SCHEME,DATA_SRC,COMMENTS,ADDDBY,ADDDTTM,MODBY,MODDTTM,CONFIDENCE,CRITICALITY,GlobalID,created_user,created_date,last_edited_user,last_edited_date,fme_dataset,fme_feature_type","Water Supply Pressure Zones","OBJECTID,Id,Zone_Name,Name_Code,Rated_Cons,GlobalID,created_user,created_date,last_edited_user,last_edited_date,Shape__Area,Shape__Length,fme_dataset,fme_feature_type","Water Supply Pumpstation","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,created_user,created_date,last_edited_user,last_edited_date,GlobalID,Shape__Area,Shape__Length,fme_dataset,fme_feature_type","Water Supply Reservoir","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,created_user,created_date,last_edited_user,last_edited_date,GlobalID,Shape__Area,Shape__Length,fme_dataset,fme_feature_type","Water Supply Treatment Plant","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,created_user,created_date,last_edited_user,last_edited_date,GlobalID,Shape__Area,Shape__Length,fme_dataset,fme_feature_type","Water Supply Valve","OBJECTID,COMPKEY,ASSETTYPE,DESCR,SERVSTAT,OWN,ZCOORD,INVERTELEV,VALVESTAT,VALVESZ,SERNO,MODELNO,MANUFCT,INSTDATE,ASBUILT,SCHEME,DATA_SRC,COMMENTS,ADDDBY,ADDDTTM,MODBY,MODDTTM,CONFIDENCE,CRITICALITY,GlobalID,created_user,created_date,last_edited_user,last_edited_date,fme_dataset,fme_feature_type"
    ATTR_ACCUM_MODE = Merge Initiator and Result
    ATTR_CONFLICT_RES = Use Result
    ATTR_IGNORE_NULLS = No
    COMBINE_GEOM = Use Result
    FEATURETYPES = Stormwater Inlet Stormwater Manhole Stormwater Meter Stormwater Node Stormwater Structure Stormwater Valve Stormwater Treatment Device
    FORMAT = ARCGISONLINEFEATURES
    INTERACT = NONE
    ORDER_RESULTS = No
    OUTPUT_FEATURES_DISPLAY = Schema and Data Features
    Stormwater Inlet -> Junction_15
    Stormwater Manhole -> Junction_15
    Stormwater Meter -> Junction_15
    Stormwater Node -> Junction_15
    Stormwater Structure -> Junction_15
    Stormwater Valve -> Junction_15
    Stormwater Treatment Device -> Junction_15
Junction_15
    -> Junction_16

Bookmark: transform: schemes2shp
Junction_12
    -> _polygons [GeometryFilter_Input]
_polygons
    COMPKEY = @Value(COMPKEY)
    GeometryRemover_Output_2 -> AttributeManager_5
AttributeManager_5
    ATTR_TABLE:
      REMOVE _creation_instance (uint64)
      REMOVE CRITICALITY (int32)
      REMOVE created_user (varchar(255))
      REMOVE created_date (datetime)
      REMOVE last_edited_user (varchar(255))
      REMOVE last_edited_date (datetime)
      REMOVE GlobalID (varchar(38))
      REMOVE Shape__Area (real64)
      REMOVE Shape__Length (real64)
      REMOVE _part_number (uint64)
      REMOVE _geometry_name (buffer)
      REMOVE point_array (buffer)
    -> DateTimeConverter_5
    -> Junction_31
DateTimeConverter_5
    DATETIME_ATTR = origin_utc ADDDTTM INSTDATE MODDTTM
    OUT_FORMAT = %Y-%m-%d %H:%M:%S
    PASSTHROUGH = NO
    REPAIR_INPUT = YES
    -> FeatureWriter_8 [Output]
    <REJECTED> -> FeatureWriter_8 [Output]
FeatureWriter_8
    DATASET = $(dir)
    DATASET_ATTR = _dataset
    FEATURE_TYPE_LIST_ATTR = _feature_types
    FORMAT = SHAPEFILE
    SHAPEFILE_COMPRESSED_FILE = No
    SHAPEFILE_DATASET_SPLITTING = Yes
    SHAPEFILE_DATETIME_STORAGE = TIMESTAMP_STRING
    SHAPEFILE_DESTINATION_DATASETTYPE_VALIDATION = Yes
    SHAPEFILE_DIMENSION = AUTO
    SHAPEFILE_ENCODING = utf-8
    SHAPEFILE_ENFORCE_ATTRIBUTE_LIMIT = No
    SHAPEFILE_MEASURES_AS_Z = No
    SHAPEFILE_PERMIT_NONASCII_FIRST_ATTRNAME = Yes
    SHAPEFILE_REQUIRE_FIRST_ATTRNAME_ALPHA = Yes
    SHAPEFILE_SPATIAL_INDEXES = NONE
    SHAPEFILE_SURFACE_SOLID_STORAGE = PATCH
    TOTAL_FEATURES_WRITTEN_ATTR = _total_features_written
Junction_31
    -> Junction_32
Junction_14
    -> _polygons_2 [GeometryFilter_Input]
_polygons_2
    COMPKEY = @Value(COMPKEY)
    GeometryRemover_Output_2 -> AttributeManager_4
AttributeManager_4
    ATTR_TABLE:
      REMOVE _creation_instance (uint64)
      SET_TO COMPKEY (buffer) = FME_CONDITIONAL:DEFAULT_VALUE'swTreatment_@Value(OBJECTID)'BOOL_OP;OR;COMPOSITE_TEST;1;TEST @Value(_part_number) > 1'swTreatment_@Value(OBJECTID)_@Value(_part_number)'FME_NUM_CONDITIONS2___
      REMOVE created_user (varchar(255))
      REMOVE created_date (datetime)
      REMOVE last_edited_user (varchar(255))
      REMOVE last_edited_date (datetime)
      REMOVE GlobalID (varchar(38))
      REMOVE Shape__Area (real64)
      REMOVE Shape__Length (real64)
      REMOVE _part_number (uint64)
      REMOVE _geometry_name (buffer)
      REMOVE point_array (buffer)
    USER_EXPOSED_ATTRIBUTES = OBJECTID
    -> DateTimeConverter_8
    -> Junction_29
DateTimeConverter_8
    DATETIME_ATTR = origin_utc ADDDTTM MODDTTM
    OUT_FORMAT = %Y-%m-%d %H:%M:%S
    PASSTHROUGH = NO
    REPAIR_INPUT = YES
    -> FeatureWriter_10 [Output]
    <REJECTED> -> FeatureWriter_10 [Output]
FeatureWriter_10
    DATASET = $(dir)
    DATASET_ATTR = _dataset
    FEATURE_TYPE_LIST_ATTR = _feature_types
    FORMAT = SHAPEFILE
    SHAPEFILE_COMPRESSED_FILE = No
    SHAPEFILE_DATASET_SPLITTING = Yes
    SHAPEFILE_DATETIME_STORAGE = TIMESTAMP_STRING
    SHAPEFILE_DESTINATION_DATASETTYPE_VALIDATION = Yes
    SHAPEFILE_DIMENSION = AUTO
    SHAPEFILE_ENCODING = utf-8
    SHAPEFILE_ENFORCE_ATTRIBUTE_LIMIT = No
    SHAPEFILE_MEASURES_AS_Z = No
    SHAPEFILE_PERMIT_NONASCII_FIRST_ATTRNAME = Yes
    SHAPEFILE_REQUIRE_FIRST_ATTRNAME_ALPHA = Yes
    SHAPEFILE_SPATIAL_INDEXES = NONE
    SHAPEFILE_SURFACE_SOLID_STORAGE = PATCH
    TOTAL_FEATURES_WRITTEN_ATTR = _total_features_written
Junction_29
    -> Junction_30
Junction_18
    -> _simple_geom [Deaggregator_Input]
_simple_geom
    TOLERANCE = 1
    Generalizer_Output -> AttributeManager_3
AttributeManager_3
    ATTR_TABLE:
      REMOVE _creation_instance (uint64)
      REMOVE Ownership (varchar(255))
      REMOVE Delivery (varchar(255))
      REMOVE Maintenance (varchar(255))
      REMOVE DecisionDate (datetime)
      REMOVE VolumeRestrictions (int32)
      REMOVE GlobalID (varchar(38))
      REMOVE created_user (varchar(255))
      REMOVE created_date (datetime)
      REMOVE last_edited_user (varchar(255))
      REMOVE last_edited_date (datetime)
      REMOVE Shape__Area (real64)
      REMOVE Shape__Length (real64)
      REMOVE _part_number (uint64)
      REMOVE _geometry_name (buffer)
    -> DateTimeConverter_4
    -> Junction_33
DateTimeConverter_4
    DATETIME_ATTR = origin_utc
    OUT_FORMAT = %Y-%m-%d %H:%M:%S
    PASSTHROUGH = NO
    REPAIR_INPUT = YES
    -> FeatureWriter_9 [Output]
    <REJECTED> -> FeatureWriter_9 [Output]
FeatureWriter_9
    DATASET = $(dir)
    DATASET_ATTR = _dataset
    FEATURE_TYPE_LIST_ATTR = _feature_types
    FORMAT = SHAPEFILE
    SHAPEFILE_COMPRESSED_FILE = No
    SHAPEFILE_DATASET_SPLITTING = Yes
    SHAPEFILE_DATETIME_STORAGE = TIMESTAMP_STRING
    SHAPEFILE_DESTINATION_DATASETTYPE_VALIDATION = Yes
    SHAPEFILE_DIMENSION = AUTO
    SHAPEFILE_ENCODING = utf-8
    SHAPEFILE_ENFORCE_ATTRIBUTE_LIMIT = No
    SHAPEFILE_MEASURES_AS_Z = No
    SHAPEFILE_PERMIT_NONASCII_FIRST_ATTRNAME = Yes
    SHAPEFILE_REQUIRE_FIRST_ATTRNAME_ALPHA = Yes
    SHAPEFILE_SPATIAL_INDEXES = NONE
    SHAPEFILE_SURFACE_SOLID_STORAGE = PATCH
    TOTAL_FEATURES_WRITTEN_ATTR = _total_features_written
Junction_33
    -> Junction_34

Bookmark: checks: compkey duplicates
Junction_32 [off]
    -> UniqueValueLogger_3
UniqueValueLogger_3
    VAL = @Value(COMPKEY)
    -> Tester_3
Tester_3
    BOOL_OP = OR
    TEST_CLAUSE = TEST @Value(_count) > 1
    TEST_MODE = TEST
Junction_30 [off]
    -> swTreatment
swTreatment: UniqueValueLogger
    VAL = @Value(COMPKEY)
    -> Tester_2
Tester_2
    BOOL_OP = OR
    TEST_CLAUSE = TEST @Value(_count) > 1
    TEST_MODE = TEST
Junction_34 [off]
    -> UniqueValueLogger_4
UniqueValueLogger_4
    VAL = @Value(OBJECTID)
    -> Tester_4
Tester_4
    BOOL_OP = OR
    TEST_CLAUSE = TEST @Value(_count) > 1
    TEST_MODE = TEST
Junction_40 [off]
    -> UniqueValueLogger_2
UniqueValueLogger_2
    VAL = @Value(COMPKEY)
    -> Tester_7
Tester_7
    BOOL_OP = OR
    TEST_CLAUSE = TEST @Value(_count) > 1
    TEST_MODE = TEST
Junction_36 [off]
    -> UniqueValueLogger_5
UniqueValueLogger_5
    VAL = @Value(COMPKEY)
    -> Tester_5
Tester_5
    BOOL_OP = OR
    TEST_CLAUSE = TEST @Value(_count) > 1
    TEST_MODE = TEST
Junction_38 [off]
    -> swMain
swMain: UniqueValueLogger
    VAL = @Value(COMPKEY)
    -> Tester_6
Tester_6
    BOOL_OP = OR
    TEST_CLAUSE = TEST @Value(_count) > 1
    TEST_MODE = TEST
Junction_28 [off]
    -> swNodes
swNodes: UniqueValueLogger
    VAL = @Value(COMPKEY)
    -> Tester
Tester
    BOOL_OP = OR
    TEST_CLAUSE = TEST @Value(_count) > 1
    TEST_MODE = TEST

Bookmark: transform: links2csv
Junction_8
    -> _startend_3 [CoordinateExtractor_Input_1]
_startend_3
    AttributeCreator_Output -> _linestring_3 [ArcStroker_Input]
_linestring_3
    GeometryRemover_Output_1 -> DateTimeConverter_3
    GeometryRemover_Output_1 -> Junction_39
DateTimeConverter_3
    DATETIME_ATTR = ADDDTTM INSTDATE MODDTTM
    OUT_FORMAT = %Y%m%d%H%M%S
    PASSTHROUGH = YES
    REPAIR_INPUT = YES
    -> DateTimeConverter_9
    <REJECTED> -> DateTimeConverter_9
DateTimeConverter_9
    DATETIME_ATTR = created_date last_edited_date
    OUT_FORMAT = %Y%m%d
    PASSTHROUGH = YES
    REPAIR_INPUT = YES
    -> FeatureWriter_3 [Output00]
    <REJECTED> -> FeatureWriter_3 [Output00]
FeatureWriter_3
    CSV2_COORDINATE_SYSTEM_GRANULARITY = FEATURE_TYPE
    CSV2_DELIMITER = ,
    CSV2_ENCODING = UTF-8
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = if_needed
    CSV2_QUALIFY_FIELD_VALUES = if_needed
    CSV2_ROW_TERMINATION = System
    CSV2_TREAT_EMBEDDED_FIELD_QUALIFIERS_AS_UNSAFE = Yes
    CSV2_WRITE_BOM_FOR_UNICODE = Yes
    CSV2_WRITE_FIELD_NAMES = firstrow
    CSV2_WRITE_SCHEMA_FILE = NO
    DATASET = $(dir)
    DATASET_ATTR = _dataset
    FEATURE_TYPE_LIST_ATTR = _feature_types
    FORMAT = CSV2
    TOTAL_FEATURES_WRITTEN_ATTR = _total_features_written
Junction_39
    -> Junction_40
Junction_7
    -> _startend_2 [CoordinateExtractor_Input_1]
_startend_2
    AttributeCreator_Output -> _linestring_2 [ArcStroker_Input]
    AttributeCreator_Output -> Junction_9
_linestring_2
    GeometryRemover_Output_1 -> AttributeCreator
    GeometryRemover_Output_1 -> Junction_35
AttributeCreator
    ATTR_TABLE:
      SET_TO UPNODE (varchar(200)) = @Value(COMPKEY)_US
      SET_TO DWNNODE (varchar(200)) = @Value(COMPKEY)_DS
    -> DateTimeConverter_7
DateTimeConverter_7
    DATETIME_ATTR = ADDDTTM INSTDATE created_date MODDTTM last_edited_date
    OUT_FORMAT = %Y%m%d%H%M%S
    PASSTHROUGH = YES
    REPAIR_INPUT = YES
    -> FeatureWriter_2 [Output00]
    <REJECTED> -> FeatureWriter_2 [Output00]
FeatureWriter_2
    CSV2_COORDINATE_SYSTEM_GRANULARITY = FEATURE_TYPE
    CSV2_DELIMITER = ,
    CSV2_ENCODING = UTF-8
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = if_needed
    CSV2_QUALIFY_FIELD_VALUES = if_needed
    CSV2_ROW_TERMINATION = System
    CSV2_TREAT_EMBEDDED_FIELD_QUALIFIERS_AS_UNSAFE = Yes
    CSV2_WRITE_BOM_FOR_UNICODE = Yes
    CSV2_WRITE_FIELD_NAMES = firstrow
    CSV2_WRITE_SCHEMA_FILE = NO
    DATASET = $(dir)
    DATASET_ATTR = _dataset
    FEATURE_TYPE_LIST_ATTR = _feature_types
    FORMAT = CSV2
    TOTAL_FEATURES_WRITTEN_ATTR = _total_features_written
Junction_35
    -> Junction_36
Junction_9
    -> Junction_10
Junction_10
    -> AttributeKeeper
    -> AttributeKeeper_2
AttributeKeeper
    CREATE_BULK_MODE_FEATURES = NO
    KEEP_ATTRS = COMPKEY,x_end,y_end
    -> AttributeManager
AttributeManager
    ATTR_TABLE:
      SET_TO id (varchar(200)) = @Value(COMPKEY)_DS
      RENAME_SET_VALUE x_end > x (real64)
      RENAME_SET_VALUE y_end > y (real64)
    -> FeatureWriter_7 [Output]
AttributeKeeper_2
    CREATE_BULK_MODE_FEATURES = NO
    KEEP_ATTRS = COMPKEY,x_start,y_start
    -> AttributeManager_2
AttributeManager_2
    ATTR_TABLE:
      SET_TO id (varchar(200)) = @Value(COMPKEY)_US
      RENAME_SET_VALUE x_start > x (real64)
      RENAME_SET_VALUE y_start > y (real64)
    USER_EXPOSED_ATTRIBUTES = x_end,y_end
    -> FeatureWriter_7 [Output]
FeatureWriter_7
    CSV2_COORDINATE_SYSTEM_GRANULARITY = FEATURE_TYPE
    CSV2_DELIMITER = ,
    CSV2_ENCODING = UTF-8
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = if_needed
    CSV2_QUALIFY_FIELD_VALUES = if_needed
    CSV2_ROW_TERMINATION = System
    CSV2_TREAT_EMBEDDED_FIELD_QUALIFIERS_AS_UNSAFE = Yes
    CSV2_WRITE_BOM_FOR_UNICODE = Yes
    CSV2_WRITE_FIELD_NAMES = firstrow
    CSV2_WRITE_SCHEMA_FILE = NO
    DATASET = $(dir)
    DATASET_ATTR = _dataset
    FEATURE_TYPE_LIST_ATTR = _feature_types
    FORMAT = CSV2
    TOTAL_FEATURES_WRITTEN_ATTR = _total_features_written
Junction_5
    -> _startend [CoordinateExtractor_Input_1]
_startend
    AttributeCreator_Output -> _linestring [ArcStroker_Input]
_linestring
    GeometryRemover_Output_1 -> DateTimeConverter_6
    GeometryRemover_Output_1 -> Junction_37
DateTimeConverter_6
    DATETIME_ATTR = ADDDTTM INSTDATE created_date MODDTTM last_edited_date
    OUT_FORMAT = %Y%m%d%H%M%S
    PASSTHROUGH = YES
    REPAIR_INPUT = YES
    -> DateTimeConverter_10
    <REJECTED> -> DateTimeConverter_10
DateTimeConverter_10
    DATETIME_ATTR = created_date last_edited_date
    OUT_FORMAT = %Y%m%d
    PASSTHROUGH = YES
    REPAIR_INPUT = YES
    -> FeatureWriter_6 [Output00]
    <REJECTED> -> FeatureWriter_6 [Output00]
FeatureWriter_6
    CSV2_COORDINATE_SYSTEM_GRANULARITY = FEATURE_TYPE
    CSV2_DELIMITER = ,
    CSV2_ENCODING = UTF-8
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = if_needed
    CSV2_QUALIFY_FIELD_VALUES = if_needed
    CSV2_ROW_TERMINATION = System
    CSV2_TREAT_EMBEDDED_FIELD_QUALIFIERS_AS_UNSAFE = Yes
    CSV2_WRITE_BOM_FOR_UNICODE = Yes
    CSV2_WRITE_FIELD_NAMES = firstrow
    CSV2_WRITE_SCHEMA_FILE = NO
    DATASET = $(dir)
    DATASET_ATTR = _dataset
    FEATURE_TYPE_LIST_ATTR = _feature_types
    FORMAT = CSV2
    TOTAL_FEATURES_WRITTEN_ATTR = _total_features_written
Junction_37
    -> Junction_38

Bookmark: transform: nodes2csv
Junction_16
    -> _nodes [CoordinateExtractor_Input]
_nodes
    GeometryRemover_Output -> AttributeValueMapper
    GeometryRemover_Output -> Junction_19
AttributeValueMapper
    DEFAULT_VALUE = @Value(INSTDATE)
    LUT = Feb 2019,20190201000000,June 2020,20200601000000
    MAPPING_DIRECTION = FORWARD
    SRC = INSTDATE
    VAL_ATTR = INSTDATE
    -> AttributeCreator_2
AttributeCreator_2
    ATTR_TABLE:
      SET_TO INSTDATE (datetime) = FME_CONDITIONAL:DEFAULT_VALUE'@Value(INSTDATE)'BOOL_OP;OR;COMPOSITE_TEST;1;TEST @Value(INSTDATE) = 000000'FME_NULL_VALUE'BOOL_OP;OR;COMPOSITE_TEST;1;TEST @StringLength(@Value(INSTDATE)) = 8'@Value(INSTDATE)000000'BOOL_OP;OR;COMPOSITE_TEST;1;TEST @StringLength(@Value(INSTDATE)) = 4'@Value(INSTDATE)0101000000'FME_NUM_CONDITIONS4___
      SET_TO FEATURE (varchar(50)) = @Value(fme_feature_type)
    -> DateTimeConverter_2
    -> Junction_27
DateTimeConverter_2
    DATETIME_ATTR = ADDDTTM INSTDATE MODDTTM
    IN_FORMAT = FME
    OUT_FORMAT = %Y%m%d%H%M%S
    PASSTHROUGH = YES
    REPAIR_INPUT = YES
    -> DateTimeConverter_11
    <REJECTED> -> DateTimeConverter_11
DateTimeConverter_11
    DATETIME_ATTR = created_date last_edited_date
    IN_FORMAT = FME
    OUT_FORMAT = %Y%m%d
    PASSTHROUGH = YES
    REPAIR_INPUT = YES
    -> TestFilter
    <REJECTED> -> TestFilter
TestFilter
    DEFAULT_VALUE = <UNFILTERED>
    PASSED_TEST_GROUP_OUTPUT = FIRST
    TEST_LIST = "BOOL_OP,OR,COMPOSITE_TEST,""""""1"""""",TEST_CLAUSE,TEST @Value(fme_feature_type) = Stormwater Inlet",swInlet,"BOOL_OP,OR,COMPOSITE_TEST,""""""1"""""",TEST_CLAUSE,TEST @Value(fme_feature_type) = Stormwater Manhole",swManhole,"BOOL_OP,OR,COMPOSITE_TEST,""""""1"""""",TEST_CLAUSE,TEST @Value(fme_feature_type) = Stormwater Node",swNode,"BOOL_OP,OR,COMPOSITE_TEST,""""""1"""""",TEST_CLAUSE,TEST @Value(fme_feature_type) = Stormwater Structure",swStructure,"BOOL_OP,OR,COMPOSITE_TEST,""""""1"""""",TEST_CLAUSE,TEST @Value(fme_feature_type) = Stormwater Treatment Device",swTreatment,"BOOL_OP,OR,COMPOSITE_TEST,""""""1"""""",TEST_CLAUSE,TEST @Value(fme_feature_type) = Stormwater Valve",swValve,"BOOL_OP,OR,COMPOSITE_TEST,""""""1"""""",TEST_CLAUSE,TEST @Value(fme_feature_type) = Stormwater Meter",swMeter
    swInlet -> FeatureWriter [Output]
    swManhole -> FeatureWriter [Output]
    swNode -> FeatureWriter [Output]
    swStructure -> FeatureWriter [Output]
    swTreatment -> FeatureWriter [Output]
    swValve -> FeatureWriter [Output]
    swMeter -> FeatureWriter [Output]
FeatureWriter
    CSV2_COORDINATE_SYSTEM_GRANULARITY = FEATURE_TYPE
    CSV2_DELIMITER = ,
    CSV2_ENCODING = UTF-8
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = if_needed
    CSV2_QUALIFY_FIELD_VALUES = if_needed
    CSV2_ROW_TERMINATION = System
    CSV2_TREAT_EMBEDDED_FIELD_QUALIFIERS_AS_UNSAFE = Yes
    CSV2_WRITE_BOM_FOR_UNICODE = Yes
    CSV2_WRITE_FIELD_NAMES = firstrow
    CSV2_WRITE_SCHEMA_FILE = NO
    DATASET = $(dir)
    DATASET_ATTR = _dataset
    FEATURE_TYPE_LIST_ATTR = _feature_types
    FORMAT = CSV2
    TOTAL_FEATURES_WRITTEN_ATTR = _total_features_written
Junction_27
    -> Junction_28
Junction_19
    -> Junction_20

Bookmark: need to sepnd some time correcting erroneous datetimes
Junction_20
    -> AttributeKeeper_3
AttributeKeeper_3
    CREATE_BULK_MODE_FEATURES = NO
    KEEP_ATTRS = INSTDATE,OBJECTID
    -> Sorter
Sorter
    SORT_PARM = INSTDATE NATURAL ASCENDING
    SORTED -> AttributeValueMapper_2
AttributeValueMapper_2
    DEFAULT_VALUE = @Value(INSTDATE)
    LUT = 000000,FME_NULL_VALUE,Feb 2019,20190101000000,June 2020,20200601000000
    MAPPING_DIRECTION = FORWARD
    SRC = INSTDATE
    VAL_ATTR = INSTDATE
    -> AttributeCreator_3
AttributeCreator_3
    ATTR_TABLE = SET_TO INSTDATE (datetime) = FME_CONDITIONAL:DEFAULT_VALUE'_FME_NO_OP_'BOOL_OP;OR;COMPOSITE_TEST;1;TEST @StringLength(@Value(INSTDATE)) = 8'@Value(INSTDATE)000000'BOOL_OP;OR;COMPOSITE_TEST;1;TEST @StringLength(@Value(INSTDATE)) = 4'@Value(INSTDATE)0101000000'FME_NUM_CONDITIONS3___
    -> DateTimeConverter
DateTimeConverter
    DATETIME_ATTR = INSTDATE
    IN_FORMAT = %Y%m%d$
    OUT_FORMAT = %Y%m%d%H%M%S
    PASSTHROUGH = NO
    REPAIR_INPUT = YES
    <REJECTED> -> DateTimeConverter__Rejected_
DateTimeConverter__Rejected_: Logger
    LOG_FEATURE = LOG_ONLY
    MAXCOORDS = 20
    MAXFEATS = 20
    MESSAGE = Feature is:
    SEVERITY = INFO

FME custom transformer UniqueValueLogger
Description
This transformer lists all of the unique values for a chosen attribute alongside  a count attribute of the number of occurrences of each of these values. The information is logged in both the Translation Window / Workspace log file, and stored in attributes.
This transformer is useful when you are creating a workspace and need to know the possible values to use in a filter.
Input Ports
Input: This transformer accepts any features with an attribute.
Output Ports
Output: Features are output with the attribute selected as the unique value to filter, and a new attribute containing the number of occurrences of each unique value. All other attributes are removed. 
_count: Number of occurrences of each unique value.
_value: Unique values of selected attribute.
Parameters
Attribute to Analyze: Select the attribute for the transformer to run analysis on. 
Notes
Transformer alternatives:
Duplicate Filter - Consider using this transformer if you are looking to get a list of unique values and do not need a _count attribute 
StatisticsCalculator - Setting the Group By mode to the attribute to analyze will produce the same result as this transformer, it may beuse If you would like to gather other statistics as well as count of the unique attributes.

Parameters:
- VAL =   # Attribute to Analyze

Input (input)
    -> AttributeCreator

Bookmark: Count unique attribute values
AttributeCreator
    ATTR_TABLE = SET_TO _value = $(VAL)
    -> AttributeKeeper
Note: Remove unwanted / attributes
AttributeKeeper
    CREATE_BULK_MODE_FEATURES = No
    KEEP_ATTRS = _value
    -> Aggregator
Note: Create aggregates of / features, grouped by / the target attribute value
Aggregator
    ACCUM_ATTRS_NAME = Merge Incoming Attributes
    AGGREGATE_TYPE = Homogeneous Collection (If Possible)
    COUNT_ATTR = _count
    GROUP_BY = _value
    MODE = Geometry - Assemble One Level
    SEP = ,
    AGGREGATE -> StringConcatenator
Note: Concatenate unique values / with their occurrence counts
StringConcatenator
    ACTION = Create New Attribute
    PARM_LINE = fme_basicstring:14%1%14%1:@Value(_value),@Value(_count)
    VAL_ATTR = _concatenated
    -> Sorter
Note: Sort output based on / occurrence count and / attribute value
Sorter
    SORT_PARM = _count NUMERIC DESCENDING _value ALPHA ASCENDING
    SORTED -> ListBuilder
    SORTED -> AttributeManager

Bookmark: Create output
AttributeManager
    ATTR_TABLE = REMOVE _concatenated
    -> Output (output)
Output (output)

Bookmark: Log unique attribute values
Note: Turn all input features / Into a single list
ListBuilder
    LIST_NAME = _list
    -> ListConcatenator
Note: Concatenate values of / the list into an attribute
ListConcatenator
    DROP_EMPTY_PARTS = No
    LIST_ATTR = _list{}._concatenated
    VAL_ATTR = UNIQUE VALUES
    -> StringConcatenator_2
Note: Add header
StringConcatenator_2
    ACTION = Create New Attribute
    PARM_LINE = "\n\nVALUE, COUNT\n@Value(UNIQUE VALUES)\n"
    VAL_ATTR = UNIQUE VALUES
    -> AttributeRemover_2
Note: Remote the list
AttributeRemover_2
    LIST_ATTRS = _list{}
    -> Logger
Note: Log the single feature / that contains the / output attribute
Logger
    LOG_FEATURE = LOG_RECORD
    MAXCOORDS = 1
    MAXFEATS = 1
    MESSAGE = Unique values:
    SEVERITY = INFO

FME custom transformer _nodes

CoordinateExtractor_Input (input)
    -> CoordinateExtractor
GeometryRemover_Output (output)

Bookmark: New Bookmark
CoordinateExtractor
    LIST_NAME = _indices
    MODE = All Coordinates
    -> AttributeCreator
AttributeCreator
    ATTR_TABLE:
      SET_TO x (varchar(200)) = @Value(_indices{0}.x)
      SET_TO y (varchar(200)) = @Value(_indices{0}.y)
    -> GeometryRemover
GeometryRemover
    REMOVE_COORDSYS = No
    -> GeometryRemover_Output (output)

FME custom transformer _simple_geom

Parameters:
- TOLERANCE = 1   # Generalization Tolerance

Deaggregator_Input (input)
    -> Deaggregator
SliverOutput (output)
Generalizer_Output (output)

Bookmark: New Bookmark
Deaggregator
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> Generalizer
Generalizer
    ALG_TEXT = Douglas (Generalize)
    PRESERVE = No
    PRESERVE_PATHS = No
    TOLERANCE = $(TOLERANCE)
    -> DonutHoleExtractor
DonutHoleExtractor
    DEAGGREGATE_INPUT = No
    OUTERSHELL -> Generalizer_Output (output)
    OUTERSHELL -> AreaGapAndOverlapCleaner
    <REJECTED> -> DonutHoleExtractor__Rejected_
AreaGapAndOverlapCleaner
    CLEANING_TOLERANCE = 5
    CONNECT_Z_MODE = First Wins
    DEAGGREGATE_INPUT = NO
    FILL_ALL_GAPS = No
    MEASURE_TYPE = Continuous
    MISSING_VAL_MODE = Compute
    REPAIR_METHOD = Longest Boundary
    REPAIRED -> SliverOutput (output)
DonutHoleExtractor__Rejected_: Logger
    LOG_FEATURE = LOG_ONLY
    MAXCOORDS = 20
    MAXFEATS = 20
    MESSAGE = Feature is:
    SEVERITY = INFO

FME custom transformer _polygons

Parameters:
- COMPKEY = @Value(COMPKEY)

GeometryFilter_Input (input)
    -> GeometryFilter
GeometryRemover_Output_2 (output)

Bookmark: New Bookmark
GeometryFilter
    FILTER_MODE = SIMPLE
    FILTER_MULTI = FILTER_TYPES]Area]FME_CONTROLLER_QUERY_FILE]]FME_CONTROLLER_CHOICE]Simple
    Area -> Deaggregator_5
Deaggregator_5
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> AttributeCreator_5
AttributeCreator_5
    ATTR_TABLE = SET_TO id (varchar(200)) = FME_CONDITIONAL:DEFAULT_VALUE'@Value(COMPKEY)'BOOL_OP;OR;COMPOSITE_TEST;1;TEST _part_number ATTRIBUTE_HAS_A_VALUE _FME_BLANK_STRING_'@Value(COMPKEY)_@Value(_part_number)'FME_NUM_CONDITIONS2___
    -> GeometryExtractor
GeometryExtractor
    ATTR = point_array
    KIND_LONG = OGC Well Known Text
    OGCVERSION = 1.2
    OGC_WKT_PRECISION_DISPLAY = 64-bit
    REMOVE_GEOMETRY = No
    -> StringReplacer
StringReplacer
    CASE = NO
    FIND_TEXT = POLYGON (
    NO_MATCH = _FME_NO_OP_
    REGEXP = NO
    SRC_ATTRS = point_array
    -> StringReplacer_2
StringReplacer_2
    CASE = NO
    FIND_TEXT = (
    NO_MATCH = _FME_NO_OP_
    REGEXP = NO
    REPLACE_TEXT = {
    SRC_ATTRS = point_array
    -> StringReplacer_3
StringReplacer_3
    CASE = NO
    FIND_TEXT = ))
    NO_MATCH = _FME_NO_OP_
    REGEXP = NO
    REPLACE_TEXT = }
    SRC_ATTRS = point_array
    -> StringReplacer_4
StringReplacer_4
    CASE = NO
    FIND_TEXT = " "
    NO_MATCH = _FME_NO_OP_
    REGEXP = NO
    REPLACE_TEXT = ,
    SRC_ATTRS = point_array
    -> GeometryRemover_Output_2 (output)

FME custom transformer _startend

CoordinateExtractor_Input_1 (input)
    -> CoordinateExtractor
AttributeCreator_Output (output)

Bookmark: New Bookmark
CoordinateExtractor
    LIST_NAME = _indices
    MODE = All Coordinates
    -> ListElementCounter
    <REJECTED> -> CoordinateExtractor__Rejected_
CoordinateExtractor__Rejected_: Logger
    LOG_FEATURE = LOG_ONLY
    MAXCOORDS = 20
    MAXFEATS = 20
    MESSAGE = Feature is:
    SEVERITY = INFO
ListElementCounter
    CNT_ATTR = _element_count
    LIST_NAME = _indices{}
    -> AttributeCreator
AttributeCreator
    ATTR_TABLE:
      SET_TO x_start (real64) = @Value(_indices{0}.x)
      SET_TO y_start (real64) = @Value(_indices{0}.y)
      SET_TO x_end (real64) = @Value(_indices{@Evaluate(@Value(_element_count)-1)}.x)
      SET_TO y_end (real64) = @Value(_indices{@Evaluate(@Value(_element_count)-1)}.y)
    -> AttributeCreator_Output (output)

FME custom transformer _linestring

ArcStroker_Input (input)
    -> ArcStroker
GeometryRemover_Output_1 (output)

Bookmark: New Bookmark
ArcStroker
    MAKE_POLY = No
    NUM = 0
    STROKE_CHOICE = Number of Interpolated Edges
    STROKED -> GeometryExtractor
GeometryExtractor
    ATTR = point_array
    KIND_LONG = OGC Well Known Text
    OGCVERSION = 1.2
    OGC_WKT_PRECISION_DISPLAY = 64-bit
    REMOVE_GEOMETRY = No
    -> StringReplacer
    <REJECTED> -> GeometryExtractor__Rejected_
StringReplacer
    CASE = NO
    FIND_TEXT = LINESTRING (
    NO_MATCH = _FME_NO_OP_
    REGEXP = NO
    REPLACE_TEXT = {
    SRC_ATTRS = point_array
    -> StringReplacer_2
StringReplacer_2
    CASE = NO
    FIND_TEXT = )
    NO_MATCH = _FME_NO_OP_
    REGEXP = NO
    REPLACE_TEXT = }
    SRC_ATTRS = point_array
    -> StringReplacer_3
StringReplacer_3
    CASE = NO
    FIND_TEXT = " "
    NO_MATCH = _FME_NO_OP_
    REGEXP = NO
    REPLACE_TEXT = ,
    SRC_ATTRS = point_array
    -> GeometryRemover
GeometryRemover
    REMOVE_COORDSYS = No
    -> GeometryRemover_Output_1 (output)
GeometryExtractor__Rejected_: Logger
    LOG_FEATURE = LOG_ONLY
    MAXCOORDS = 20
    MAXFEATS = 20
    MESSAGE = Feature is:
    SEVERITY = INFO
