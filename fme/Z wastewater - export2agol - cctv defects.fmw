FME workspace Z wastewater - export2agol - cctv defects.fmw

Parameters:
- DestDataset_ARCGISPORTALFEATURES = https://gis.qldc.govt.nz/portal   # Portal URL

Writers:
- ARCGISPORTALFEATURES_1: ARCGISPORTALFEATURES to $(DestDataset_ARCGISPORTALFEATURES) in NZTM

Bookmark: datetime
Creator
    GEOMTYPE = Geometry Object
    NUM = 1
    CREATED -> DateTimeStamper
DateTimeStamper
    DATETIME_ATTR = origin_utc
    INCLUDE_FRAC_SECONDS = YES
    INCLUDE_OFFSET = NO
    STAMP_TYPE = datetime
    TIMEZONE = utc
    -> AttributeCreator
AttributeCreator
    ATTR_TABLE = SET_TO origin_utc (buffer) = @int(@Value(origin_utc))
    -> Junction_9
Junction_9
    -> Junction_10

Bookmark: extract: cctv surveys spatial and data
Junction_10
    -> FeatureReader [INITIATOR]
FeatureReader
    ATTRIBUTES =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
    ATTR_ACCUM_MODE = Merge Initiator and Result
    ATTR_CONFLICT_RES = Use Result
    ATTR_IGNORE_NULLS = No
    COMBINE_GEOM = Use Result
    DATASET = $(FME_MF_DIR_ENCODED)imports\iam_network\wastewater\MIF\*.MIF
    FEATURETYPES = CCTV conduit details
    FORMAT = MIF
    INTERACT = NONE
    MIF_ENCODED_ATTRS = mif_text_string
    MIF_ENCODED_ATTR_NAMES = YES
    MIF_ENCODING = fme-source-encoding
    MIF_PRESERVE_DUPLICATES = YES
    MIF_UNENCODED_ATTR_PREFIX = fme_ mif_
    MIF_USE_SEARCH_ENVELOPE = NO
    ORDER_RESULTS = No
    OUTPUT_FEATURES_DISPLAY = Schema and Data Features
    CCTV conduit details -> Counter_2
    INITIATOR -> FeatureReader_2 [INITIATOR]
FeatureReader_2
    ATTRIBUTES = CSV,"id,video_no,photo_no,distance,cd,code,video_file,diameter,Joint,clock_at,clock_to,percentage,intrusion,remarks,characterisation1,characterisation2,detail_image,video_no2,service_score,structural_score,characterisation3"
    ATTR_ACCUM_MODE = Merge Initiator and Result
    ATTR_CONFLICT_RES = Use Result
    ATTR_IGNORE_NULLS = No
    COMBINE_GEOM = Use Result
    CSV2_CASE_SENSITIVE_FIELD_NAMES = Yes
    CSV2_CHUNK_SIZE = 100000
    CSV2_DATA_START_LINE = 2
    CSV2_DATE_INPUT_FORMAT = ISO
    CSV2_DELIMITER = auto
    CSV2_DELIMITER_DETECTION_ALGORITHM = EQUAL_FIELDS_PER_LINE
    CSV2_ENCODING = windows-1252
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = No
    CSV2_SCAN_ADDITIONAL_FIELDS = No
    CSV2_SCAN_MAX_ROWS = 250000
    CSV2_SCAN_TYPES = Yes
    CSV2_SKIP_DUPLICATE_DELIMITERS = No
    CSV2_STRING_TYPE_ATTRIBUTE_HANDLING = EXPLICIT_WIDTH
    CSV2_SUPPORTED_READER_ARCHIVE_EXTENSIONS = csv.gz,txt.gz
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_TYPE_ATTRIBUTE_HANDLING = STANDARD_TYPES
    CSV2_USE_CUSTOM_SCHEMA = NO
    DATASET = $(FME_MF_DIR_ENCODED)exports\CSV\network.csv_cams_cctv_survey_details.csv
    FORMAT = CSV2
    INTERACT = NONE
    ORDER_RESULTS = No
    OUTPUT_FEATURES_DISPLAY = Schema and Data Features
    CSV -> Counter
Counter
    CNT_ATTR = _count_2
    SCOPE = Local
    START = 0
    -> Junction_3
Junction_3
    -> Junction_4
Counter_2
    CNT_ATTR = _count_1
    SCOPE = Local
    START = 0
    -> Junction
Junction
    -> Junction_2

Bookmark: transform: spatial join of data to CSV file
Junction_4
    -> FeatureMerger [SUPPLIER]
Junction_2
    -> AttributeKeeper
AttributeKeeper
    CREATE_BULK_MODE_FEATURES = NO
    KEEP_ATTRS = _count_1,id
    -> FeatureMerger [REQUESTOR]
FeatureMerger
    ATTR_ACCUM_MODE = Merge Supplier
    ATTR_CONFLICT_RES = Use Requestor
    IGNORE_NULLS = No
    JOIN_KEYS = @Value(_count_1) @Value(_count_2) AUTO
    MERGE_TYPE = Attributes Only
    PROCESS_DUPS = NO
    REJECT_NULL_MISSING_KEYS = No
    SUPPLIERS_FIRST = No
    MERGED -> AttributeRemover
AttributeRemover
    REMOVE_ATTRS = _count_1,_count_2,_creation_instance,_matched_records
    -> Junction_5
Junction_5
    -> Junction_6

Bookmark: validation: code
Junction_6
    -> UniqueValueLogger_4
    -> AttributeValueMapper
UniqueValueLogger_4
    VAL = @Value(code)
    -> Sorter
Sorter
    SORT_PARM = _value NATURAL ASCENDING
AttributeValueMapper
    DEFAULT_VALUE = @Value(code)
    LUT = -,FME_NULL_VALUE,#N/A,FME_NULL_VALUE
    MAPPING_DIRECTION = FORWARD
    SRC = code
    VAL_ATTR = code
    -> AttributeCreator_2
AttributeCreator_2
    ATTR_TABLE = SET_TO code (varchar(5)) = @UpperCase(@Value(code))
    -> Junction_7
Junction_7
    -> Junction_8

Bookmark: validation: cd
Junction_8
    -> UniqueValueLogger_5
    -> Junction_11
UniqueValueLogger_5
    VAL = @Value(cd)
    -> Sorter_2
Sorter_2
    SORT_PARM = _value NATURAL ASCENDING
Junction_11
    -> Junction_12

Bookmark: validation: distance
Junction_12
    -> Tester
    -> Junction_13
Tester
    BOOL_OP = OR
    TEST_CLAUSE:
      TEST distance ATTRIBUTE_IS_MISSING ""
      TEST distance ATTRIBUTE_IS_EMPTY ""
      TEST distance ATTRIBUTE_VALUE_NULL ""
    TEST_MODE = TEST
Junction_13
    -> Junction_14

Bookmark: load: 2 agol
Junction_14
    -> cctv_survey_defects (writer ARCGISPORTALFEATURES_1)
cctv_survey_defects (writer ARCGISPORTALFEATURES_1)
    attributes: id String, video_no Double, photo_no String(64), distance Double, cd String(3), code String(12), video_file String, diameter Double, Joint String(1), clock_at Integer, clock_to Integer, percentage Double, intrusion Double, remarks String, characterisation1 String(4), characterisation2 String(4), detail_image String, video_no2 String(12), service_score Double, structural_score Double, characterisation3 String(20), origin_utc Date

FME custom transformer UniqueValueLogger
Description
This transformer lists all of the unique values for a chosen attribute alongside  a count attribute of the number of occurrences of each of these values. The information is logged in both the Translation Window / Workspace log file, and stored in attributes.
This transformer is useful when you are creating a workspace and need to know the possible values to use in a filter.
Input Ports
Input: This transformer accepts any features with an attribute.
Output Ports
Output: Features are output with the attribute selected as the unique value to filter, and a new attribute containing the number of occurrences of each unique value. All other attributes are removed. 
_count: Number of occurrences of each unique value.
_value: Unique values of selected attribute.
Parameters
Attribute to Analyze: Select the attribute for the transformer to run analysis on. 
Notes
Transformer alternatives:
Duplicate Filter - Consider using this transformer if you are looking to get a list of unique values and do not need a _count attribute 
StatisticsCalculator - Setting the Group By mode to the attribute to analyze will produce the same result as this transformer, it may beuse If you would like to gather other statistics as well as count of the unique attributes.

Parameters:
- VAL =   # Attribute to Analyze

Input (input)
    -> AttributeCreator

Bookmark: Count unique attribute values
AttributeCreator
    ATTR_TABLE = SET_TO _value = $(VAL)
    -> AttributeKeeper
Note: Remove unwanted / attributes
AttributeKeeper
    CREATE_BULK_MODE_FEATURES = No
    KEEP_ATTRS = _value
    -> Aggregator
Note: Create aggregates of / features, grouped by / the target attribute value
Aggregator
    ACCUM_ATTRS_NAME = Merge Incoming Attributes
    AGGREGATE_TYPE = Homogeneous Collection (If Possible)
    COUNT_ATTR = _count
    GROUP_BY = _value
    MODE = Geometry - Assemble One Level
    SEP = ,
    AGGREGATE -> StringConcatenator
Note: Concatenate unique values / with their occurrence counts
StringConcatenator
    ACTION = Create New Attribute
    PARM_LINE = fme_basicstring:14%1%14%1:@Value(_value),@Value(_count)
    VAL_ATTR = _concatenated
    -> Sorter
Note: Sort output based on / occurrence count and / attribute value
Sorter
    SORT_PARM = _count NUMERIC DESCENDING _value ALPHA ASCENDING
    SORTED -> ListBuilder
    SORTED -> AttributeManager

Bookmark: Create output
AttributeManager
    ATTR_TABLE = REMOVE _concatenated
    -> Output (output)
Output (output)

Bookmark: Log unique attribute values
Note: Turn all input features / Into a single list
ListBuilder
    LIST_NAME = _list
    -> ListConcatenator
Note: Concatenate values of / the list into an attribute
ListConcatenator
    DROP_EMPTY_PARTS = No
    LIST_ATTR = _list{}._concatenated
    VAL_ATTR = UNIQUE VALUES
    -> StringConcatenator_2
Note: Add header
StringConcatenator_2
    ACTION = Create New Attribute
    PARM_LINE = "\n\nVALUE, COUNT\n@Value(UNIQUE VALUES)\n"
    VAL_ATTR = UNIQUE VALUES
    -> AttributeRemover_2
Note: Remote the list
AttributeRemover_2
    LIST_ATTRS = _list{}
    -> Logger
Note: Log the single feature / that contains the / output attribute
Logger
    LOG_FEATURE = LOG_RECORD
    MAXCOORDS = 1
    MAXFEATS = 1
    MESSAGE = Unique values:
    SEVERITY = INFO
