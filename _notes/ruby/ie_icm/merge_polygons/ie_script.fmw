FME workspace ie_script.fmw

Parameters:
- DestDataset_MITAB = $(FME_MF_DIR)gis   # Destination MapInfo Folder
- DestDataset_MIF = $(FME_MF_DIR)gis   # Destination MapInfo Folder

Writers:
- MIF_1: MIF to $(DestDataset_MIF)
- MITAB_1: MITAB to $(DestDataset_MITAB)

Bookmark: extract: mid mif data for subcatchments from model(s)
Creator
    GEOMTYPE = Geometry Object
    NUM = 1
    CREATED -> FeatureReader [INITIATOR]
FeatureReader
    ATTRIBUTES = subcatchment,"subcatchment_id,system_type,drains_to,node_id,link_suffix,to_subcatchment_id,_2d_pt_id,lateral_weights,limit_drain_capacity,capacity_limit,exceed_flow_type,total_area,contributing_area,x,y,catchment_slope,ukwir_soil_runoff,soil_class_type,soil_class,soil_class_host,max_soil_moisture_capacity,curve_number,drying_time,rainfall_profile,evaporation_profile,area_average_rain,catchment_dimension,unit_hydrograph_id,snow_pack_id,baseflow_calc,soil_moist_def,srm_runoff_coeff,srm_k1,srm_k2,srm_tdly,arma_id,output_lag,bypass_runoff,uh_definition,tc_method,overland_flow_time,flood_wave_celerity,equivalent_roughness,hydraulic_radius,pwri_coefficient,time_of_concentration,tc_timestep_factor,tc_time_to_peak_factor,time_to_peak,base_time,lag_time,peaking_coeff,uh_peak,uh_kink,non_linear_routing_method,lag_time_method,storage_factor,storage_exponent,internal_routing,percent_routed,rafts_per_surface,degree_urbanisation,rafts_adapt_factor,rafts_b,rafts_n,connectivity,wastewater_profile,population,trade_flow,additional_foul_flow,base_flow,trade_profile,ground_id,ground_node,baseflow_lag,baseflow_recharge,land_use_id,pdm_descriptor_id,area_measurement_type,area_absolute_1,area_absolute_2,area_absolute_3,area_absolute_4,area_absolute_5,area_absolute_6,area_absolute_7,area_absolute_8,area_absolute_9,area_absolute_10,area_absolute_11,area_absolute_12,area_percent_1,area_percent_2,area_percent_3,area_percent_4,area_percent_5,area_percent_6,area_percent_7,area_percent_8,area_percent_9,area_percent_10,area_percent_11,area_percent_12,notes,user_number_1,user_number_2,user_number_3,user_number_4,user_number_5,user_number_6,user_number_7,user_number_8,user_number_9,user_number_10,user_text_1,user_text_2,user_text_3,user_text_4,user_text_5,user_text_6,user_text_7,user_text_8,user_text_9,user_text_10"
    ATTR_ACCUM_MODE = Only Use Result
    COMBINE_GEOM = Use Result
    DATASET = $(FME_MF_DIR_ENCODED)exports\**\*.MIF
    FORMAT = MIF
    INTERACT = NONE
    MIF_ENCODED_ATTRS = mif_text_string
    MIF_ENCODED_ATTR_NAMES = YES
    MIF_ENCODING = fme-source-encoding
    MIF_PRESERVE_DUPLICATES = YES
    MIF_UNENCODED_ATTR_PREFIX = fme_ mif_
    MIF_USE_SEARCH_ENVELOPE = NO
    OUTPUT_FEATURES_DISPLAY = Schema and Data Features
    subcatchment -> Junction
Junction
    -> Junction_2

Bookmark: transform: into flow monitor catchment areas
Junction_2
    -> Tester
Tester
    BOOL_OP = OR
    TEST_CLAUSE = CASE_INSENSITIVE_TEST @Value(system_type) = foul
    TEST_MODE = CASE_INSENSITIVE_TEST
    PASSED -> Deaggregator
Deaggregator
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> Dissolver
Dissolver
    ACCUM_INPUT_ATTRS = Use Attributes From One Feature
    CLEANING_TOLERANCE = Automatic
    CONNECT_Z_MODE = First Wins
    DEAGGREGATE_INPUT = Yes
    GROUP_BY = land_use_id
    LIST_NAME = _list
    AREA -> Junction_3
Junction_3
    -> Junction_4

Bookmark: load: 2gis file
Junction_4
    -> AttributeKeeper
AttributeKeeper
    CREATE_BULK_MODE_FEATURES = NO
    KEEP_ATTRS = land_use_id
    -> land_use_id (writer MIF_1)
    -> land_use_id (writer MITAB_1)
land_use_id (writer MIF_1) [off]
    attributes: land_use_id char(100)
land_use_id (writer MITAB_1)
    attributes: land_use_id char(100)
