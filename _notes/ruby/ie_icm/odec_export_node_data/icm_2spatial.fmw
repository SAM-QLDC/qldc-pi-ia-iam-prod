FME workspace icm_2spatial.fmw

Parameters:
- DEST = EPSG:4326   # Destination Coordinate System
- fme_table_handling = DROP_CREATE

Bookmark: extract: mid/mif data from ICM
Creator
    GEOMTYPE = Geometry Object
    NUM = 1
    CREATED -> FeatureReader [INITIATOR]
FeatureReader
    ATTRIBUTES = conduit,"us_node_id,link_suffix,ds_node_id,link_type,asset_id,sewer_reference,system_type,branch_id,is_merged,asset_uid,infonet_us_node_id,infonet_ds_node_id,infonet_link_suffix,us_settlement_eff,ds_settlement_eff,solution_model,min_computational_nodes,critical_sewer_category,taking_off_reference,conduit_material,design_group,site_condition,ground_condition,conduit_type,min_space_step,slot_width,connection_coefficient,shape,conduit_width,conduit_height,springing_height,sediment_depth,number_of_barrels,roughness_type,bottom_roughness_CW,top_roughness_CW,bottom_roughness_Manning,top_roughness_Manning,bottom_roughness_N,top_roughness_N,bottom_roughness_HW,top_roughness_HW,conduit_length,inflow,gradient,capacity,us_invert,ds_invert,us_headloss_type,ds_headloss_type,us_headloss_coeff,ds_headloss_coeff,base_height,infiltration_coeff_base,infiltration_coeff_side,fill_material_conductivity,porosity,diff1d_type,diff1d_d0,diff1d_d1,diff1d_d2,inlet_type_code,reverse_flow_model,equation,k,m,c,y,us_ki,us_ko,outlet_type_code,equation_o,k_o,m_o,c_o,y_o,ds_ki,ds_ko,notes,user_number_1,user_number_2,user_number_3,user_number_4,user_number_5,user_number_6,user_number_7,user_number_8,user_number_9,user_number_10,user_text_1,user_text_2,user_text_3,user_text_4,user_text_5,user_text_6,user_text_7,user_text_8,user_text_9,user_text_10",node,"node_id,node_type,asset_id,system_type,connection_type,lateral_node_id,lateral_link_suffix,asset_uid,infonet_id,x,y,ground_level,flood_level,shaft_area_additional,shaft_area_add_comp,shaft_area_add_simplify,shaft_area_add_ncorrect,shaft_area_additional_total,chamber_area_additional,chamber_area_add_comp,chamber_area_add_simplify,chamber_area_add_ncorrect,chamber_area_additional_total,chamber_roof,chamber_floor,chamber_area,shaft_area,flood_type,element_area_factor_2d,flooding_discharge_coeff,benching_method,_2d_link_type,floodable_area,flood_depth_1,flood_depth_2,flood_area_1,flood_area_2,base_area,perimeter,infiltration_coeff,porosity,vegetation_level,liner_level,infiltratn_coeff_abv_vegn,infiltratn_coeff_abv_liner,infiltratn_coeff_blw_liner,relative_stages,inlet_input_type,inlet_type,cross_slope,grate_width,grate_length,opening_length,opening_height,gutter_depression,lateral_depression,velocity_splashover,debris,depth_weir,clear_opening,head_discharge_id,flow_efficiency_id,inlet_UE_a,inlet_UE_b,n_gullies,num_transverse_bars,num_longitudinal_bars,num_diagonal_bars,min_area_inc_voids,area_of_voids,half_road_width,notes,user_number_1,user_number_2,user_number_3,user_number_4,user_number_5,user_number_6,user_number_7,user_number_8,user_number_9,user_number_10,user_text_1,user_text_2,user_text_3,user_text_4,user_text_5,user_text_6,user_text_7,user_text_8,user_text_9,user_text_10",polygon,"polygon_id,category_id,area,notes,user_number_1,user_number_2,user_number_3,user_number_4,user_number_5,user_number_6,user_number_7,user_number_8,user_number_9,user_number_10,user_text_1,user_text_2,user_text_3,user_text_4,user_text_5,user_text_6,user_text_7,user_text_8,user_text_9,user_text_10",subcatchment,"subcatchment_id,system_type,drains_to,node_id,link_suffix,to_subcatchment_id,_2d_pt_id,lateral_weights,limit_drain_capacity,capacity_limit,exceed_flow_type,total_area,contributing_area,x,y,catchment_slope,ukwir_soil_runoff,soil_class_type,soil_class,soil_class_host,max_soil_moisture_capacity,curve_number,drying_time,rainfall_profile,evaporation_profile,area_average_rain,catchment_dimension,unit_hydrograph_id,snow_pack_id,baseflow_calc,soil_moist_def,srm_runoff_coeff,srm_k1,srm_k2,srm_tdly,arma_id,output_lag,bypass_runoff,uh_definition,tc_method,overland_flow_time,flood_wave_celerity,equivalent_roughness,hydraulic_radius,pwri_coefficient,time_of_concentration,tc_timestep_factor,tc_time_to_peak_factor,time_to_peak,base_time,lag_time,peaking_coeff,uh_peak,uh_kink,non_linear_routing_method,lag_time_method,storage_factor,storage_exponent,internal_routing,percent_routed,rafts_per_surface,degree_urbanisation,rafts_adapt_factor,rafts_b,rafts_n,connectivity,wastewater_profile,population,trade_flow,additional_foul_flow,base_flow,trade_profile,ground_id,ground_node,baseflow_lag,baseflow_recharge,land_use_id,pdm_descriptor_id,area_measurement_type,area_absolute_1,area_absolute_2,area_absolute_3,area_absolute_4,area_absolute_5,area_absolute_6,area_absolute_7,area_absolute_8,area_absolute_9,area_absolute_10,area_absolute_11,area_absolute_12,area_percent_1,area_percent_2,area_percent_3,area_percent_4,area_percent_5,area_percent_6,area_percent_7,area_percent_8,area_percent_9,area_percent_10,area_percent_11,area_percent_12,notes,user_number_1,user_number_2,user_number_3,user_number_4,user_number_5,user_number_6,user_number_7,user_number_8,user_number_9,user_number_10,user_text_1,user_text_2,user_text_3,user_text_4,user_text_5,user_text_6,user_text_7,user_text_8,user_text_9,user_text_10"
    ATTR_ACCUM_MODE = Only Use Result
    COMBINE_GEOM = Use Result
    COORDSYS = NZTM
    DATASET = $(FME_MF_DIR_ENCODED)exports\**\*.MIF
    FORMAT = MIF
    INTERACT = NONE
    MIF_ENCODED_ATTRS = mif_text_string
    MIF_ENCODED_ATTR_NAMES = YES
    MIF_ENCODING = fme-source-encoding
    MIF_PRESERVE_DUPLICATES = YES
    MIF_UNENCODED_ATTR_PREFIX = fme_ mif_
    MIF_USE_SEARCH_ENVELOPE = NO
    OUTPUT_FEATURES_DISPLAY = Schema and Data Features
    conduit -> Junction_3
    polygon -> Junction
    subcatchment -> Junction_7
Junction_3
    -> Junction_4
Junction
    -> Junction_2
Junction_7
    -> Junction_8

Bookmark: transform: conduits
Junction_4
    -> Reprojector_2
Reprojector_2
    DEST = $(DEST)
    INTERPOLATION_TYPE_NAME = Nearest Neighbor
    RASTER_CELL_SIZE = Preserve Cells
    RASTER_TOLERANCE = 0.0
    REPROJECTED -> AttributeKeeper_2
AttributeKeeper_2
    CREATE_BULK_MODE_FEATURES = NO
    KEEP_ATTRS = asset_id,ds_node_id,link_suffix,link_type,us_node_id,system_type,solution_model,conduit_material,conduit_width,shape,capacity,conduit_length,user_number_1,user_number_2,user_number_3,user_number_4,user_number_5,user_number_6,user_number_7,user_number_8,user_number_9,user_number_10,user_text_1,user_text_2,user_text_3,user_text_4,user_text_5,user_text_6,user_text_7,user_text_8,user_text_9,user_text_10
    -> AttributeRenamer_2
AttributeRenamer_2
    ATTR_TABLE:
      RENAME_SET_DEFAULT user_text_4 > val_year
      RENAME_SET_DEFAULT user_text_5 > val_perc_cg
      RENAME_SET_DEFAULT user_text_6 > val_rul_years
      RENAME_SET_DEFAULT user_number_1 > design_adwf
      RENAME_SET_DEFAULT user_number_2 > design_pf
      RENAME_SET_DEFAULT user_number_3 > design_di
      RENAME_SET_DEFAULT user_number_4 > design_ii
      RENAME_SET_DEFAULT user_number_5 > design_pwwf
      RENAME_SET_DEFAULT user_number_6 > design_bifu_allowance
      RENAME_SET_DEFAULT user_number_7 > design_spare_pwwf
      RENAME_SET_DEFAULT user_number_8 > design_velocity
    MISSING_INPUT_ATTRS = REMOVE
    -> BulkAttributeRemover
BulkAttributeRemover
    ATTR_EXP = ^user
    -> AttributeManager_2
AttributeManager_2
    USER_EXPOSED_ATTRIBUTES = perc_cg,rul_years
    -> Junction_11
Junction_11
    -> Junction_12

Bookmark: load: 2geodatabase
Junction_12
    -> 2gdb [Output00]
    -> 2mapinfo [Output00]
Junction_10
    -> 2gdb [Output]
    -> 2mapinfo [Output]
Junction_16
    -> 2gdb [Output02]
    -> 2mapinfo [Output01]
2gdb: FeatureWriter [off]
    DATASET = $(FME_MF_DIR_ENCODED)esri\design_code.gdb
    DATASET_ATTR = _dataset
    FEATURE_TYPE_LIST_ATTR = _feature_types
    FORMAT = GEODATABASE_FILE
    GEODATABASE_FILE_ANNOTATION_UNITS = unknown_units
    GEODATABASE_FILE_COMPRESS_AT_END = no
    GEODATABASE_FILE_COORDINATE_SYSTEM_GRANULARITY = FEATURE_TYPE
    GEODATABASE_FILE_DEFAULT_Z_VALUE = 0
    GEODATABASE_FILE_DESTINATION_DATASETTYPE_VALIDATION = Yes
    GEODATABASE_FILE_DUMP_FAILED_FEATURES = no
    GEODATABASE_FILE_ENABLE_FAST_DELETES = yes
    GEODATABASE_FILE_ENABLE_LOAD_ONLY_MODE = no
    GEODATABASE_FILE_GRID_1 = 0
    GEODATABASE_FILE_HAS_MEASURES = no
    GEODATABASE_FILE_HAS_Z_VALUES = auto_detect
    GEODATABASE_FILE_IGNORE_FAILED_FEATURE_ENTRY = no
    GEODATABASE_FILE_MAX_NUMBER_FAILED_FEATURES = -1
    GEODATABASE_FILE_OVERWRITE_GEODB = YES
    GEODATABASE_FILE_REQUESTED_GEODATABASE_VERSION = CURRENT
    GEODATABASE_FILE_SIMPLIFY_GEOM = No
    GEODATABASE_FILE_SIMPLIFY_NETWORK_FEATURES = no
    GEODATABASE_FILE_TRANSACTION = 0
    GEODATABASE_FILE_TRANSACTION_INTERVAL = 1000
    GEODATABASE_FILE_TRANSACTION_TYPE = TRANSACTIONS
    GEODATABASE_FILE_VALIDATE_FEATURES = no
    GEODATABASE_FILE_XY_SCALE = 0
    GEODATABASE_FILE_X_ORIGIN = 0
    GEODATABASE_FILE_Y_ORIGIN = 0
    GEODATABASE_FILE_Z_ORIGIN = 0
    GEODATABASE_FILE_Z_SCALE = 0
    TOTAL_FEATURES_WRITTEN_ATTR = _total_features_written
2mapinfo: FeatureWriter
    DATASET = $(FME_MF_DIR_ENCODED)mapinfo
    DATASET_ATTR = _dataset
    FEATURE_TYPE_LIST_ATTR = _feature_types
    FORMAT = MITAB
    MITAB_BUILD_OPTIMAL_SPATIAL_INDEX = no
    MITAB_COORDINATE_SYSTEM_GRANULARITY = FEATURE_TYPE
    MITAB_DESTINATION_DATASETTYPE_VALIDATION = Yes
    MITAB_ENCODING = windows-1252
    MITAB_MAP_LARGEINT_TO_DECIMAL = yes
    MITAB_PLUGIN_MAX_CHANNELS = 100
    MITAB_STROKE_ARCS = no
    MITAB_TWO_POINT_LINE_AS_POLYLINE = no
    MITAB_VERSION = 900
    MITAB_WRITE_REGION_CENTROIDS = no
    MITAB__USE_SOURCE_BOUNDING_BOX = no
    TOTAL_FEATURES_WRITTEN_ATTR = _total_features_written

Bookmark: transform: polygons
Junction_2
    -> DuplicateFilter
DuplicateFilter
    INPUT_ORDERED_CHOICE = No
    KEYATTR = polygon_id
    UNIQUE -> Reprojector
Reprojector
    DEST = $(DEST)
    INTERPOLATION_TYPE_NAME = Nearest Neighbor
    RASTER_CELL_SIZE = Preserve Cells
    RASTER_TOLERANCE = 0.0
    REPROJECTED -> AttributeRenamer
AttributeRenamer
    ATTR_TABLE:
      RENAME_SET_DEFAULT user_text_6 > headship_cur
      RENAME_SET_DEFAULT user_text_7 > headship_med
      RENAME_SET_DEFAULT user_text_8 > headship_m2l
      RENAME_SET_DEFAULT user_text_9 > headship_lng
      RENAME_SET_DEFAULT user_text_10 > headship_mpd
      RENAME_SET_DEFAULT user_number_1 > population_cur
      RENAME_SET_DEFAULT user_number_2 > population_med
      RENAME_SET_DEFAULT user_number_3 > population_m2l
      RENAME_SET_DEFAULT user_number_4 > population_lng
      RENAME_SET_DEFAULT user_number_5 > population_mpd
      RENAME_SET_DEFAULT user_number_10 > growth_mpd
      RENAME_SET_DEFAULT notes > design_ground
    MISSING_INPUT_ATTRS = REMOVE
    -> BulkAttributeRemover_2
BulkAttributeRemover_2
    ATTR_EXP = ^user
    -> AttributeManager
AttributeManager
    USER_EXPOSED_ATTRIBUTES = notes
    -> Junction_9
Junction_9
    -> Junction_10

Bookmark: transform: subcatchments
Junction_8
    -> Reprojector_4
Reprojector_4
    DEST = $(DEST)
    INTERPOLATION_TYPE_NAME = Nearest Neighbor
    RASTER_CELL_SIZE = Preserve Cells
    RASTER_TOLERANCE = 0.0
    REPROJECTED -> AttributeKeeper_4
AttributeKeeper_4
    CREATE_BULK_MODE_FEATURES = NO
    KEEP_ATTRS = subcatchment_id,land_use_id,population
    -> GeometryExtractor
GeometryExtractor
    ATTR = _geometry
    KIND_LONG = OGC Well Known Text
    OGCVERSION = 1.2
    OGC_WKT_PRECISION_DISPLAY = 64-bit
    REMOVE_GEOMETRY = No
    -> TestFilter
TestFilter
    DEFAULT_VALUE = <UNFILTERED>
    PASSED_TEST_GROUP_OUTPUT = FIRST
    TEST_LIST = "BOOL_OP,OR,COMPOSITE_TEST,""""""1"""""",TEST_CLAUSE,CASE_INSENSITIVE_TEST @Value(_geometry) BEGINS_WITH POLYGON",polygon,"BOOL_OP,OR,COMPOSITE_TEST,""""""1"""""",TEST_CLAUSE,CASE_INSENSITIVE_TEST @Value(_geometry) BEGINS_WITH POINT",point
    polygon -> AttributeManager_3
AttributeManager_3
    ATTR_TABLE = REMOVE _geometry
    -> Junction_15
Junction_15
    -> Junction_16
