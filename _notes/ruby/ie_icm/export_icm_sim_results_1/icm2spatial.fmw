FME workspace icm2spatial.fmw

Bookmark: extract: all mid mif files
Creator
    GEOMTYPE = Geometry Object
    NUM = 1
    CREATED -> FeatureReader [INITIATOR]
FeatureReader
    ATTRIBUTES = Links,"link_id,us_node_id,ds_node_id,link_suffix,sim_id,event_name,profile_type,return_period,duration,ds_INVERT,ds_QCUM,HEIGHT,LENGTH,ds_DEPTH,ds_FLOW,ds_FROUDE,ds_totalhead,ds_VEL,QINFLNK,QLINK,Surcharge,us_DEPTH,us_FLOW,us_FROUDE,us_totalhead,us_VEL,maxsurchargestate,PFC,QLICUM,TYPE,us_INVERT,us_QCUM",Nodes,"node_id,sim_id,event_name,profile_type,return_period,duration,FLOOD_LEVEL,DEPNOD,FloodDepth,FloodVolume,FLVOL,QINFNOD,QNODE,QRAIN,VOLUME,PCVOLBAL,QINCUM,VFLOOD,VGROUND,VOLBAL",Subcatchments,"subcatchment_id,sim_id,event_name,profile_type,return_period,duration,EFFRAIN,EVAPPROF,EVAPRATE,GRNDSTOR,LOSTTOGW,NAPI,QCATCH,QFOUL,QGROUND,QINFGRND,QINFILT,QINFSOIL,QSOIL,QSURF01,QSURF02,QSURF03,QSURF04,QTRADE,RAINFALL,RUNOFF,SOILSTOR,QBASE,RAINPROF","TVD connector","id,sim_id,event_name,profile_type,return_period,duration,TVD_EV,TVD_Q,TVD_R,TVD_Z"
    ATTR_ACCUM_MODE = Only Use Result
    COMBINE_GEOM = Use Result
    COORDSYS = NZTM
    DATASET = $(FME_MF_DIR_ENCODED)exports\**\*.MIF
    FORMAT = MIF
    INTERACT = NONE
    MIF_ENCODED_ATTRS = mif_text_string
    MIF_ENCODED_ATTR_NAMES = YES
    MIF_ENCODING = fme-source-encoding
    MIF_PRESERVE_DUPLICATES = YES
    MIF_UNENCODED_ATTR_PREFIX = fme_ mif_
    MIF_USE_SEARCH_ENVELOPE = NO
    OUTPUT_FEATURES_DISPLAY = Schema and Data Features
    Links -> Reprojector
    Nodes -> Reprojector_2
    Subcatchments -> Reprojector_3
    TVD connector -> Reprojector_4
Reprojector
    DEST = EPSG:4326
    INTERPOLATION_TYPE_NAME = Nearest Neighbor
    RASTER_CELL_SIZE = Preserve Cells
    RASTER_TOLERANCE = 0.0
Reprojector_2
    DEST = EPSG:4326
    INTERPOLATION_TYPE_NAME = Nearest Neighbor
    RASTER_CELL_SIZE = Preserve Cells
    RASTER_TOLERANCE = 0.0
Reprojector_3
    DEST = EPSG:4326
    INTERPOLATION_TYPE_NAME = Nearest Neighbor
    RASTER_CELL_SIZE = Preserve Cells
    RASTER_TOLERANCE = 0.0
Reprojector_4
    DEST = EPSG:4326
    INTERPOLATION_TYPE_NAME = Nearest Neighbor
    RASTER_CELL_SIZE = Preserve Cells
    RASTER_TOLERANCE = 0.0
