FME workspace data.fmw

Parameters:
- SourceDataset_FILEGDB = $(FME_MF_DIR)exports\**\*.gdb   # File Geodatabase
- DestDataset_XLSXW = $(FME_MF_DIR)exports\data.xlsx   # Destination Microsoft Excel File

Readers:
- FILEGDB_1: FILEGDB from $(SourceDataset_FILEGDB)

Writers:
- XLSXW_1: XLSXW to $(DestDataset_XLSXW)

Bookmark: extract: gis data from infoasset
_/__Node (reader FILEGDB_1)
    attributes: OID objectid, access_action text(40), access_breadth text(10), access_shape text(10), access_time text(40), access_type text(50), access_width text(10), adjustment_ring_height double, adjustment_ring_material text(50), adjustment_ring_type text(50), asset_id text(40), attend_to_bench smallint, attend_to_chamber smallint, attend_to_cover smallint, attend_to_other smallint, attend_to_shaft smallint, attend_to_step smallint, barcode text(255), bench_lining text(50), bench_material text(50), bench_present text(50), category text(2), CH2MHill_overall_ii_grade int, CH2MHill_overall_sii_grade int, CH2MHill_overall_total_grad int, chamber_condition int, chamber_construction text(10), chamber_dim double, chamber_dim_2 double, chamber_floor_depth double,
      chamber_shape text(40), chamber_unit_length double, channel_exposure text(50), channel_installed smallint, channel_material text(50), channel_type text(50), chimney_clear_opening double, chimney_depth double, chimney_ini text(50), chimney_lining_exterior text(50), chimney_lining_interior text(50), chimney_material1 text(50), chimney_material2 text(50), city text(64), clear_opening double, condition_grade int, cone_depth double, cone_lining_exterior text(50), cone_lining_interior text(50), cone_material text(50), cone_type text(50), coordinate_system text(50), cover_assembly text(40), cover_bearing_surface_dia double, cover_bearing_surface_dia_width double, cover_condition int, cover_condition_boltsmissing smallint, cover_condition_broken smallint, cover_condition_corroded smallint, cover_condition_cracked smallint,
      cover_condition_missing smallint, cover_condition_restraint_defect smallint, cover_condition_restraint_miss smallint, cover_condition_sound smallint, cover_dim double, cover_dim_2 double, cover_duty text(10), cover_frame_fit text(50), cover_hinged smallint, cover_insert_type text(50), cover_level double, cover_locked smallint, cover_material text(40), cover_shape text(10), cover_type_bolted smallint, cover_type_gasketed smallint, cover_type_hatch_double smallint, cover_type_hatch_single smallint, cover_type_inner_cover smallint, cover_type_lamphole smallint, cover_type_locking smallint, cover_type_solid smallint, cover_type_vented smallint, criticality text(5), cross_slope double, current_value double, debris double, drainage_area text(15), drainage_code text(10), flow_depth double,
      frame_bearing_surface_depth double, frame_bearing_surface_width double, frame_clear_open_diam double, frame_clear_open_width double, frame_condition_broken smallint, frame_condition_coated smallint, frame_condition_corroded smallint, frame_condition_cracked smallint, frame_condition_missing smallint, frame_condition_sound smallint, frame_depth double, frame_material text(50), frame_offset_distance double, frame_seal_inflow text(50), gas_type text(40), gps_survey_date date, grade_to_invert double, grate_length double, grate_width double, ground_level double, gutter_depression double, hole_diameter text(50), hole_number int, inlet_type text(30), insert_condition_corroded smallint, insert_condition_cracked smallint, insert_condition_insertfell smallint, insert_condition_leaking smallint, insert_condition_poorlyfitting smallint, insert_condition_sound smallint,
      inspection_cost double, inspection_status text(50), install_cost double, internal_image_filename text(255), internal_image_ref text(30), lat_channel_id text(40), lat_circ_location smallint, lat_distance double, lat_ds_node_id text(40), lat_link_suffix text(1), lat_us_node_id text(40), lateral_depression double, leveler_condition text(40), leveler_material text(40), lifetime int, location text(100), location_code text(30), location_details text(255), location_image_filename text(255), location_image_ref text(30), location_sketch_filename text(255), location_sketch_ref text(30), main_comment text(40), maintenance_condition int, material text(10), mobile_uid text(100), node_id text(40), node_type text(10), num_ladders smallint, num_landings int,
      num_regulating smallint, num_steps smallint, opening_height double, opening_length double, owner text(64), plan_sketch_filename text(255), plan_sketch_ref text(30), po_number text(15), potential_for_runoff text(50), rehab_cost double, replace_cost double, rim_to_grade double, rim_to_invert double, ring_condition_broken smallint, ring_condition_corroded smallint, ring_condition_cracked smallint, ring_condition_leaking smallint, ring_condition_poorinstall smallint, ring_condition_sound smallint, seal_condition_cracked smallint, seal_condition_loose smallint, seal_condition_missing smallint, seal_condition_offset smallint, seal_condition_sound smallint, security text(10), shaft_access text(40), shaft_condition int, shaft_depth double, shaft_dim double, shaft_dim_2 double,
      shaft_material text(40), side_entry smallint, silt_depth double, site_condition text(40), site_managed_by text(40), soffit_type text(10), status text(10), step_material text(50), street text(64), surcharge_height double, surface_type_asphalt smallint, surface_type_concretecollar smallint, surface_type_concretepavement smallint, surface_type_grassdirt smallint, surface_type_gravel smallint, surface_type_other smallint, survey_date date, system_type text(10), toxic_atmosphere smallint, uid text(32), user_date_1 date, user_date_2 date, user_date_3 date, user_date_4 date, user_date_5 date, user_number_1 double, user_number_10 double, user_number_11 double, user_number_12 double, user_number_13 double,
      user_number_14 double, user_number_15 double, user_number_16 double, user_number_17 double, user_number_18 double, user_number_19 double, user_number_2 double, user_number_20 double, user_number_21 double, user_number_22 double, user_number_23 double, user_number_24 double, user_number_25 double, user_number_26 double, user_number_27 double, user_number_28 double, user_number_29 double, user_number_3 double, user_number_30 double, user_number_31 double, user_number_32 double, user_number_33 double, user_number_34 double, user_number_35 double, user_number_36 double, user_number_37 double, user_number_38 double, user_number_39 double, user_number_4 double, user_number_40 double,
      user_number_5 double, user_number_6 double, user_number_7 double, user_number_8 double, user_number_9 double, user_text_1 text(250), user_text_10 text(250), user_text_11 text(250), user_text_12 text(250), user_text_13 text(250), user_text_14 text(250), user_text_15 text(250), user_text_16 text(250), user_text_17 text(250), user_text_18 text(250), user_text_19 text(250), user_text_2 text(250), user_text_20 text(250), user_text_21 text(250), user_text_22 text(250), user_text_23 text(250), user_text_24 text(250), user_text_25 text(250), user_text_26 text(250), user_text_27 text(250), user_text_28 text(250), user_text_29 text(250), user_text_3 text(250), user_text_30 text(250), user_text_31 text(250),
      user_text_32 text(250), user_text_33 text(250), user_text_34 text(250), user_text_35 text(250), user_text_36 text(250), user_text_37 text(250), user_text_38 text(250), user_text_39 text(250), user_text_4 text(250), user_text_40 text(250), user_text_5 text(250), user_text_6 text(250), user_text_7 text(250), user_text_8 text(250), user_text_9 text(250), vermin smallint, wall_bysize double, wall_depth double, wall_diam double, wall_lining_exterior text(50), wall_lining_interior text(50), wall_material text(50), x double, y double, year_laid date, year_renewed int, hotlinks text(100)
    -> Junction
Junction
    -> Junction_2
_/__Pump_station (reader FILEGDB_1)
    attributes: OID objectid, access_diff text(32), access_road text(32), area_code text(40), asset_id text(40), barcode text(255), condition_grade int, confined_spaces text(20), constr_date date, criticality text(5), current_value double, date_cleaned date, date_installed date, date_renewed date, dist_to_habitation double, duty_flow double, duty_head double, fencing text(32), flow_meter_man text(40), flow_meter_model text(40), flow_meter_type text(40), gates text(32), gps_survey_date date, id_renamed text(40), inspection_cost double, install_cost double, level_controller_man text(40), level_controller_model text(40), lifetime int, location text(100),
      locked smallint, main_breaker_size double, mcc_panel_manufacturer text(40), mcc_panel_model_no text(40), mobile_uid text(100), non_op_area text(32), num_pumps int, owner text(64), photo_filename text(255), photo_ref text(30), planning_status text(20), power double, power_consumption double, pump_breaker_size double, pump_starter_size double, pump_starter_type text(40), pump_to_waste_facilities text(40), rehab_cost double, replace_cost double, roof text(32), scada_panel_serial_no text(20), scada_pole_height double, scada_signal_tower text(40), security text(10), sketch_filename text(255), sketch_ref text(30), soil_type text(10), status text(20), substructure text(32), superstructure text(32),
      surface_type text(10), surroundings text(32), survey_date date, tariff_name text(20), type text(10), type_of_starter text(40), uid text(32), user_date_1 date, user_date_2 date, user_date_3 date, user_date_4 date, user_date_5 date, user_number_1 double, user_number_10 double, user_number_11 double, user_number_12 double, user_number_13 double, user_number_14 double, user_number_15 double, user_number_16 double, user_number_17 double, user_number_18 double, user_number_19 double, user_number_2 double, user_number_20 double, user_number_21 double, user_number_22 double, user_number_23 double, user_number_24 double, user_number_25 double,
      user_number_26 double, user_number_27 double, user_number_28 double, user_number_29 double, user_number_3 double, user_number_30 double, user_number_31 double, user_number_32 double, user_number_33 double, user_number_34 double, user_number_35 double, user_number_36 double, user_number_37 double, user_number_38 double, user_number_39 double, user_number_4 double, user_number_40 double, user_number_5 double, user_number_6 double, user_number_7 double, user_number_8 double, user_number_9 double, user_text_1 text(250), user_text_10 text(250), user_text_11 text(250), user_text_12 text(250), user_text_13 text(250), user_text_14 text(250), user_text_15 text(250), user_text_16 text(250),
      user_text_17 text(250), user_text_18 text(250), user_text_19 text(250), user_text_2 text(250), user_text_20 text(250), user_text_21 text(250), user_text_22 text(250), user_text_23 text(250), user_text_24 text(250), user_text_25 text(250), user_text_26 text(250), user_text_27 text(250), user_text_28 text(250), user_text_29 text(250), user_text_3 text(250), user_text_30 text(250), user_text_31 text(250), user_text_32 text(250), user_text_33 text(250), user_text_34 text(250), user_text_35 text(250), user_text_36 text(250), user_text_37 text(250), user_text_38 text(250), user_text_39 text(250), user_text_4 text(250), user_text_40 text(250), user_text_5 text(250), user_text_6 text(250), user_text_7 text(250),
      user_text_8 text(250), user_text_9 text(250), vehicle_access text(32), vehicle_turning text(32), well_access text(32), well_area double, well_constr text(32), well_cover_level double, well_ventilation text(32), x double, y double, hotlinks text(100), FGeom_Length double, FGeom_Area double
    -> Junction_3
Junction_3
    -> Junction_4

Bookmark: transform: get hold of coords for each wastewater asset
Junction_2
    -> AttributeKeeper
Junction_4
    -> AttributeKeeper
AttributeKeeper
    CREATE_BULK_MODE_FEATURES = NO
    KEEP_ATTRS = asset_id,x,y,node_id,uid
    -> Tester
Tester
    BOOL_OP = AND
    TEST_CLAUSE:
      TEST asset_id ATTRIBUTE_HAS_A_VALUE ""
      TEST x ATTRIBUTE_HAS_A_VALUE ""
      TEST y ATTRIBUTE_HAS_A_VALUE ""
    TEST_MODE = TEST
    PASSED -> Sorter
Sorter
    SORT_PARM = uid NATURAL ASCENDING
    SORTED -> Junction_7
Junction_7
    -> Junction_8

Bookmark: extract coords
Junction_8
    -> Reprojector
Reprojector
    DEST = EPSG:4326
    INTERPOLATION_TYPE_NAME = Nearest Neighbor
    RASTER_CELL_SIZE = Preserve Cells
    RASTER_TOLERANCE = 0.0
    REPROJECTED -> GeometryExtractor
GeometryExtractor
    ATTR = _geometry
    KIND_LONG = OGC Well Known Text
    OGCVERSION = 1.1
    OGC_WKT_PRECISION_DISPLAY = 32-bit
    REMOVE_GEOMETRY = No
    -> GeometryRemover
GeometryRemover
    -> Junction_5
Junction_5
    -> Junction_6

Bookmark: load: 2excel
Junction_6
    -> AttributeManager
AttributeManager
    ATTR_TABLE:
      REMOVE x
      REMOVE y
    -> ww_assets (writer XLSXW_1)
ww_assets (writer XLSXW_1)
    attributes: uid string(32), asset_id string(40), node_id string(40), _geometry string(20)
