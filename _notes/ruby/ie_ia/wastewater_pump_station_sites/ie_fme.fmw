FME workspace ie_fme.fmw

Parameters:
- RHS = 2   # Right Value

Bookmark: create rows
Creator
    GEOMTYPE = Geometry Object
    NUM = 5
    CREATED -> AttributeValueMapper
AttributeValueMapper
    LUT = 0,C:\Program Files\Autodesk\InfoWorks ICM Ultimate 2024\iexchange.exe,1,C:\Program Files (x86)\Innovyze Workgroup Client 2023.2\iexchange.exe,2,C:\Program Files (x86)\Innovyze Workgroup Client 2021.8\iexchange.exe,3,C:\Program Files (x86)\Innovyze Workgroup Client 2021.2\iexchange.exe,4,C:\Program Files (x86)\Innovyze Workgroup Client 10.5\iexchange.exe
    MAPPING_DIRECTION = FORWARD
    SRC = _creation_instance
    VAL_ATTR = _iexchange
    -> Junction_7
Junction_7
    -> Junction_8

Bookmark: choose iexchange version
Junction_8
    -> Tester
Tester
    BOOL_OP = OR
    TEST_CLAUSE = TEST @Value(_creation_instance) = $(RHS)
    TEST_MODE = TEST
    PASSED -> AttributeCreator_2
AttributeCreator_2
    ATTR_TABLE:
      SET_TO _app = IA
      SET_TO _script = ie_script.rb
      SET_TO _folder = $(FME_MF_DIR_USERTYPED)exports
    -> Junction
Junction
    -> Junction_2

Bookmark: delete exports folder
Junction_2
    -> _del_folder
_del_folder: SystemCaller
    ATTR = _exit_code_a
    CMD = if exist "@Value(_folder)" (rmdir /s/q "@Value(_folder)")
    -> Tester_3
Tester_3
    BOOL_OP = OR
    TEST_CLAUSE = TEST @Value(_exit_code_a) = 0
    TEST_MODE = TEST
    PASSED -> Junction_3
Junction_3
    -> Junction_4

Bookmark: make exports folder
Junction_4
    -> _mkdir
_mkdir: SystemCaller
    ATTR = _exit_code_b
    CMD = mkdir "@Value(_folder)"
    -> Tester_4
Tester_4
    BOOL_OP = OR
    TEST_CLAUSE = TEST @Value(_exit_code_b) = 0
    TEST_MODE = TEST
    PASSED -> Junction_5
Junction_5
    -> Junction_6

Bookmark: create fresh set of data
Junction_6
    -> AttributeCreator_3
AttributeCreator_3
    ATTR_TABLE:
      SET_TO _batch = $(FME_MF_DIR_USERTYPED)@Value(_script)
      SET_TO _cmd = ""@Value(_iexchange)" "@Value(_batch)" /@Value(_app)"
    -> _command
_command: SystemCaller [off]
    ATTR = _exit_code_c
    CMD = @Value(_cmd)
    -> Tester_2
Tester_2
    BOOL_OP = OR
    TEST_CLAUSE = TEST @Value(_exit_code_c) = 0
    TEST_MODE = TEST
