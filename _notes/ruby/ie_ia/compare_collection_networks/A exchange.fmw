FME workspace A exchange.fmw

Parameters:
- SourceDataset_XLSXR = $(FME_MF_DIR)backend\catalogue.xlsx   # Source Microsoft Excel File(s)

Readers:
- XLSXR_1: XLSXR from $(SourceDataset_XLSXR)

Bookmark: extract: load catalogue table and now try infonet exchange
catalogue (reader XLSXR_1)
    attributes: order number(2,0), active number(2,0), app char(10), type char(3), feature char(19), snumbat char(33), iexchange char(70), batch char(66)
    -> Tester
Note: Tester [Tester] / Test Clauses: Left ValueOperatorRight Value@Value(active)=1Advanced: / Preserve Feature Order: Per Output Port
Tester
    BOOL_OP = OR
    TEST_CLAUSE = TEST @Value(active) = 1
    TEST_MODE = TEST
    PASSED -> Junction_3
Junction_3
    -> Junction_4

Bookmark: transform: create system command for each iexchange infoasset request
Junction_4
    -> _icm
Note: _icm [Tester] / Test Clauses: Left ValueOperatorRight Value@Value(type)=ICMAdvanced: / Preserve Feature Order: Per Output Port
_icm: Tester
    BOOL_OP = OR
    TEST_CLAUSE = TEST @Value(type) = ICM
    TEST_MODE = TEST
    PASSED -> AttributeCreator
AttributeCreator
    ATTR_TABLE = SET_TO system_cmd = ""@Value(iexchange)" "@Value(batch)" /@Value(type)"
    -> SystemCaller
SystemCaller
    ATTR = _exit_code
    CMD = @Value(system_cmd)
    -> Tester_2
Tester_2
    BOOL_OP = OR
    TEST_CLAUSE = TEST @Value(_exit_code) = 0
    TEST_MODE = TEST
