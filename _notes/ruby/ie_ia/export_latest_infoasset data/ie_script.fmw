FME workspace ie_script.fmw

Parameters:
- SourceDataset_GEOTIFF = $(FME_MF_DIR)gis\wellington-1953-to-nzvd2016-conversion-raster.tif   # Source GeoTIFF File(s) or URL(s)

Readers:
- GEOTIFF_1: GEOTIFF from $(SourceDataset_GEOTIFF)

Bookmark: extract: 2053 to 2016 conversion value from geotiff
GEOTIFF (reader GEOTIFF_1)
    -> RasterBandSeparator
RasterBandSeparator
    BAND_INDEX_FIELD = _band_index
    PALETTE_INDEX_FIELD = _palette_index
    RASTER_INDEX_FIELD = _raster_index
    SPLIT_BY_NAME = Band and Palette
    -> AttributeExposer
AttributeExposer
    ATTR_LIST = geotiff_private_keys{}.value
    -> Junction_11
Note: note the conversion value is taken away from 2053. / So 10m in 2053 becomes 9.6m or so in 2016
Junction_11
    -> Junction_12

Bookmark: transform: work out new ground levels
Junction_12
    -> PointOnRasterValueExtractor [RASTER]
    -> Junction_13
Junction_13
    -> Junction_14
Junction_8
    -> Tester_2
Tester_2
    BOOL_OP = AND
    TEST_CLAUSE:
      TEST x ATTRIBUTE_HAS_A_VALUE ""
      TEST y ATTRIBUTE_HAS_A_VALUE ""
    TEST_MODE = TEST
    PASSED -> Reprojector
Reprojector
    DEST = LL-WGS84
    INTERPOLATION_TYPE_NAME = Nearest Neighbor
    RASTER_CELL_SIZE = Preserve Cells
    RASTER_TOLERANCE = 0.0
    REPROJECTED -> PointOnRasterValueExtractor [POINT]
PointOnRasterValueExtractor
    INTERPOLATION_TYPE_NAME = Nearest Neighbor
    POINT -> AttributeCreator_3
AttributeCreator_3
    ATTR_TABLE = SET_TO level_2053 = FME_CONDITIONAL:DEFAULT_VALUE'FME_NULL_VALUE'BOOL_OP;OR;COMPOSITE_TEST;1;TEST level ATTRIBUTE_HAS_A_VALUE _FME_BLANK_STRING_'@round((@Value(level)+@Value(_band{0}.value)),3)'FME_NUM_CONDITIONS2___
    -> Junction_9
Junction_9
    -> Junction_10

Bookmark: transform: work out inverts
Junction_14
    -> PointOnRasterValueExtractor_2 [RASTER]
Junction_6
    -> GeometryValidator
GeometryValidator
    ISSUE_ATTR_NAME = _issues
    PRESETS = All
    REPAIR = Yes
    RULES = AREA_ORIENTATION AREA_ORIENTATION]VALID]FME_CONTROLLER_QUERY_FILE]transformers/dependencies/geometryvalidator8/AREA_ORIENTATION.fme]FME_CONTROLLER_CHOICE]AREA_ORIENTATION CONSECUTIVE_IDENTICAL_VERTICES_2D CHECK_Z]YES]TOLERANCE]0.0]FME_CONTROLLER_QUERY_FILE]transformers/dependencies/geometryvalidator8/CONSECUTIVE_IDENTICAL_VERTICES_2D.fme]FME_CONTROLLER_CHOICE]CONSECUTIVE_IDENTICAL_VERTICES_2D MISSING_TEXTURE_COORDINATES FME_CONTROLLER_QUERY_FILE]transformers/dependencies/geometryvalidator8/MISSING_TEXTURE_COORDINATES.fme]FME_CONTROLLER_CHOICE]MISSING_TEXTURE_COORDINATES MISSING_VERTEX_NORMALS FME_CONTROLLER_QUERY_FILE]transformers/dependencies/geometryvalidator8/MISSING_VERTEX_NORMALS.fme]FME_CONTROLLER_CHOICE]MISSING_VERTEX_NORMALS NAN_REMOVAL PROCESS_MEASURE]NO]FME_CONTROLLER_QUERY_FILE]transformers/dependencies/geometryvalidator8/NAN_REMOVAL.fme]FME_CONTROLLER_CHOICE]NAN_REMOVAL NULL_REMOVAL FME_CONTROLLER_QUERY_FILE]transformers/dependencies/geometryvalidator8/NULL_REMOVAL.fme]FME_CONTROLLER_CHOICE]NULL_REMOVAL OGC_VALID_CHECK OGC_VERSION]V1.2.0]LEGACY_OGC]No]FME_CONTROLLER_QUERY_FILE]transformers/dependencies/geometryvalidator8/OGC_VALID_CHECK.fme]FME_CONTROLLER_CHOICE]OGC_VALID_CHECK OGC_SIMPLE_CHECK LEGACY_OGC]No]FME_CONTROLLER_QUERY_FILE]transformers/dependencies/geometryvalidator8/OGC_SIMPLE_CHECK.fme]FME_CONTROLLER_CHOICE]OGC_SIMPLE_CHECK PLANAR_SURFACE CHECK_AREA]DO_NOT_CHECK_AREA]TOLERANCE_MODE]AUTO]TOLERANCE]<Unused>]ANGULAR_TOLERANCE_MODE]AUTO]ANGULAR_TOLERANCE]<Unused>]FME_CONTROLLER_QUERY_FILE]transformers/dependencies/geometryvalidator8/PLANAR_SURFACE.fme]FME_CONTROLLER_CHOICE]PLANAR_SURFACE SELF_INTERSECTING CHECK_HOLE_TOUCHING_POLYGON]No]CONNECT_Z_MODE_SI]FIRST_WINS]SELF_INTERSECTION_TOLERANCE]None]INTERSECT_ACROSS_MULTIS]No]FME_CONTROLLER_QUERY_FILE]transformers/dependencies/geometryvalidator8/SELF_INTERSECTING.fme]FME_CONTROLLER_CHOICE]SELF_INTERSECTING SHELL_VALIDATION FLIP_APPEARANCE_MODE]FLIP_APPEARANCES]FME_CONTROLLER_QUERY_FILE]transformers/dependencies/geometryvalidator8/SHELL_VALIDATION.fme]FME_CONTROLLER_CHOICE]SHELL_VALIDATION SOLID_VOID_REPAIR FME_CONTROLLER_QUERY_FILE]transformers/dependencies/geometryvalidator8/SOLID_VOID_REPAIR.fme]FME_CONTROLLER_CHOICE]SOLID_VOID_REPAIR TYPE_REPAIR CONNECT_Z_MODE]FIRST_WINS]ARC_ENDPOINT_TOLERANCE_MODE]Auto]ARC_ENDPOINT_TOLERANCE]<Unused>]FME_CONTROLLER_QUERY_FILE]transformers/dependencies/geometryvalidator8/TYPE_REPAIR.fme]FME_CONTROLLER_CHOICE]TYPE_REPAIR MISMATCHED_DIMENSIONS FORCE_DIMENSION]2D]MISMATCHED_Z_VAL]<Unused>]FME_CONTROLLER_QUERY_FILE]transformers/dependencies/geometryvalidator8/MISMATCHED_DIMENSIONS.fme]FME_CONTROLLER_CHOICE]MISMATCHED_DIMENSIONS MISSING_MEASURES_AND_ELEVATIONS MISSING_VALUES_MODE]SENTINEL]MISSING_MEASURES_MODE]<Unused>]SENTINEL_VALUE]0]LENGTH_DIMENSION]<Unused>]FME_CONTROLLER_QUERY_FILE]transformers/dependencies/geometryvalidator8/MISSING_MEASURES_AND_ELEVATIONS.fme]FME_CONTROLLER_CHOICE]MISSING_MEASURES_AND_ELEVATIONS SURFACE_ORIENTATION FME_CONTROLLER_QUERY_FILE]transformers/dependencies/geometryvalidator8/SURFACE_ORIENTATION.fme]FME_CONTROLLER_CHOICE]SURFACE_ORIENTATION SOLID_ORIENTATION FME_CONTROLLER_QUERY_FILE]transformers/dependencies/geometryvalidator8/SOLID_ORIENTATION.fme]FME_CONTROLLER_CHOICE]SOLID_ORIENTATION
    SUMMARY = Detailed
    PASSED -> Reprojector_2
Reprojector_2
    DEST = LL-WGS84
    INTERPOLATION_TYPE_NAME = Nearest Neighbor
    RASTER_CELL_SIZE = Preserve Cells
    RASTER_TOLERANCE = 0.0
    REPROJECTED -> CoordinateExtractor
CoordinateExtractor
    LIST_NAME = _indices
    MODE = All Coordinates
    -> GeometryExtractor
GeometryExtractor
    ATTR = _geometry
    KIND_LONG = Hex Encoded FME Binary
    REMOVE_GEOMETRY = Yes
    -> VertexCreator
VertexCreator
    MEASURE_TYPE = Continuous
    MODE_NAME = Replace with Point
    XVAL = @Value(_indices{0}.x)
    YVAL = @Value(_indices{0}.y)
    -> PointOnRasterValueExtractor_2 [POINT]
PointOnRasterValueExtractor_2
    INTERPOLATION_TYPE_NAME = Nearest Neighbor
    POINT -> GeometryRemover
GeometryRemover
    -> AttributeCreator_4
AttributeCreator_4
    ATTR_TABLE:
      SET_TO ds_2053 = FME_CONDITIONAL:DEFAULT_VALUE'FME_NULL_VALUE'BOOL_OP;OR;COMPOSITE_TEST;1;TEST ds_invert ATTRIBUTE_HAS_A_VALUE _FME_BLANK_STRING_'@round((@Value(ds_invert)+@Value(_band{0}.value)),3)'FME_NUM_CONDITIONS2___
      SET_TO us_2053 = FME_CONDITIONAL:DEFAULT_VALUE'FME_NULL_VALUE'BOOL_OP;OR;COMPOSITE_TEST;1;TEST us_invert ATTRIBUTE_HAS_A_VALUE _FME_BLANK_STRING_'@round((@Value(us_invert)+@Value(_band{0}.value)),3)'FME_NUM_CONDITIONS2___
    -> GeometryReplacer
GeometryReplacer
    KIND_LONG = Hex Encoded FME Binary
    REMOVE_ATTRIBUTE = Yes
    SOURCE = @Value(_geometry)
    -> Junction_15
Junction_15
    -> Junction_16

Bookmark: extract: infoasset data
Creator
    GEOMTYPE = Geometry Object
    NUM = 1
    CREATED -> FeatureReader [INITIATOR]
FeatureReader
    ATTRIBUTES =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
    ATTR_ACCUM_MODE = Merge Initiator and Result
    ATTR_CONFLICT_RES = Use Result
    ATTR_IGNORE_NULLS = No
    COMBINE_GEOM = Use Result
    DATASET = $(FME_MF_DIR_ENCODED)exports\**\data.gdb
    FEATURETYPES = _/__Node _/__Pipe
    FILEGDB_QUERY_FEATURE_TYPES_FOR_MERGE_FILTERS = Yes
    FILEGDB_SIMPLE_DONUT_GEOMETRY = simple
    FILEGDB_STRIP_GUID_GLOBALID_BRACES = no
    FILEGDB_USE_SEARCH_ENVELOPE = NO
    FORMAT = FILEGDB
    INTERACT = NONE
    OUTPUT_FEATURES_DISPLAY = Schema and Data Features
    _/__Node -> Junction_3
    _/__Pipe -> Junction
Junction_3
    -> Junction_4
Junction
    -> Junction_2

Bookmark: transform: links into manholes
Junction_4
    -> Tester_3
Tester_3
    BOOL_OP = COMPOSITE
    COMPOSITE_TEST = 1 AND 2
    TEST_CLAUSE:
      TEST @Value(system_type) != WWSC
      TEST @Value(status) != ABAN
    TEST_MODE = TEST
    PASSED -> AttributeCreator_2
AttributeCreator_2
    ATTR_TABLE:
      SET_TO system_type = FME_CONDITIONAL:DEFAULT_VALUE'_FME_NO_OP_'BOOL_OP;OR;COMPOSITE_TEST;1;TEST @Value(system_type) = WWCO'foul'BOOL_OP;OR;COMPOSITE_TEST;1;TEST @Value(system_type) = SWCO'storm'FME_NUM_CONDITIONS3___
      SET_TO ground_level = FME_CONDITIONAL:DEFAULT_VALUE'FME_NULL_VALUE'BOOL_OP;OR;COMPOSITE_TEST;1;TEST ground_level ATTRIBUTE_HAS_A_VALUE _FME_BLANK_STRING_'@Value(ground_level)'BOOL_OP;OR;COMPOSITE_TEST;1;TEST cover_level ATTRIBUTE_HAS_A_VALUE _FME_BLANK_STRING_'@Value(cover_level)'FME_NUM_CONDITIONS3___
      SET_TO flood_type = Lost
    -> AttributeValueMapper
AttributeValueMapper
    DEFAULT_VALUE = break
    LUT = ACMH,manhole,PSTN,storage,OTND,manhole
    MAPPING_DIRECTION = FORWARD
    SRC = node_type
    VAL_ATTR = _node_type
    -> AttributeKeeper_2
AttributeKeeper_2
    CREATE_BULK_MODE_FEATURES = NO
    KEEP_ATTRS = node_id,asset_id,system_type,x,y,ground_level,_node_type,uid
    -> AttributeManager_2
AttributeManager_2
    ATTR_TABLE:
      RENAME_SET_VALUE _node_type > node_type
      RENAME_SET_VALUE system_type > system
      RENAME_SET_VALUE ground_level > level
    USER_EXPOSED_ATTRIBUTES = OID
    -> Junction_7
Junction_7
    -> Junction_8

Bookmark: load: 2gdb
Junction_10
    -> Reprojector_3
Reprojector_3
    DEST = NZTM
    INTERPOLATION_TYPE_NAME = Nearest Neighbor
    RASTER_CELL_SIZE = Preserve Cells
    RASTER_TOLERANCE = 0.0
    REPROJECTED -> FeatureWriter [Output]
Junction_16
    -> Reprojector_4
Reprojector_4
    DEST = NZTM
    INTERPOLATION_TYPE_NAME = Nearest Neighbor
    RASTER_CELL_SIZE = Preserve Cells
    RASTER_TOLERANCE = 0.0
    REPROJECTED -> FeatureWriter [Output00]
FeatureWriter
    DATASET = $(FME_MF_DIR_ENCODED)gis
    DATASET_ATTR = _dataset
    FEATURE_TYPE_LIST_ATTR = _feature_types
    FORMAT = SHAPEFILE
    SHAPEFILE_COMPRESSED_FILE = No
    SHAPEFILE_DATASET_SPLITTING = Yes
    SHAPEFILE_DATETIME_STORAGE = TIMESTAMP_STRING
    SHAPEFILE_DESTINATION_DATASETTYPE_VALIDATION = Yes
    SHAPEFILE_DIMENSION = AUTO
    SHAPEFILE_ENCODING = utf-8
    SHAPEFILE_ENFORCE_ATTRIBUTE_LIMIT = No
    SHAPEFILE_MEASURES_AS_Z = No
    SHAPEFILE_REQUIRE_FIRST_ATTRNAME_ALPHA = Yes
    SHAPEFILE_SPATIAL_INDEXES = NONE
    SHAPEFILE_SURFACE_SOLID_STORAGE = PATCH
    TOTAL_FEATURES_WRITTEN_ATTR = _total_features_written

Bookmark: transform: links into conduits
Junction_2
    -> Tester
Tester
    BOOL_OP = COMPOSITE
    COMPOSITE_TEST = 1 AND 2
    TEST_CLAUSE:
      TEST @Value(system_type) = WWCO
      TEST @Value(status) != ABAN
    TEST_MODE = TEST
    PASSED -> AttributeCreator
AttributeCreator
    ATTR_TABLE:
      SET_TO system_type = FME_CONDITIONAL:DEFAULT_VALUE'_FME_NO_OP_'BOOL_OP;OR;COMPOSITE_TEST;1;TEST @Value(system_type) = WWCO'foul'BOOL_OP;OR;COMPOSITE_TEST;1;TEST @Value(system_type) = SWCO'storm'FME_NUM_CONDITIONS3___
      SET_TO system_type = FME_CONDITIONAL:DEFAULT_VALUE'_FME_NO_OP_'BOOL_OP;OR;COMPOSITE_TEST;1;TEST @Value(pipe_type) = TRNK'combined'FME_NUM_CONDITIONS2___
      SET_TO solution_model = FME_CONDITIONAL:DEFAULT_VALUE'Full'BOOL_OP;OR;COMPOSITE_TEST;1;TEST @Value(user_text_24) = PRES'Pressure'FME_NUM_CONDITIONS2___
      SET_TO material = FME_CONDITIONAL:DEFAULT_VALUE'FME_NULL_VALUE'BOOL_OP;OR;COMPOSITE_TEST;1;TEST pipe_material ATTRIBUTE_HAS_A_VALUE _FME_BLANK_STRING_'@Value(pipe_material)'BOOL_OP;OR;COMPOSITE_TEST;1;TEST ds_pipe_material ATTRIBUTE_HAS_A_VALUE _FME_BLANK_STRING_'@Value(ds_pipe_material)'FME_NUM_CONDITIONS3___
      SET_TO width = FME_CONDITIONAL:DEFAULT_VALUE'FME_NULL_VALUE'BOOL_OP;OR;COMPOSITE_TEST;1;TEST width ATTRIBUTE_HAS_A_VALUE _FME_BLANK_STRING_'@Value(width)'BOOL_OP;OR;COMPOSITE_TEST;1;TEST ds_width ATTRIBUTE_HAS_A_VALUE _FME_BLANK_STRING_'@Value(ds_width)'FME_NUM_CONDITIONS3___
      SET_TO height = FME_CONDITIONAL:DEFAULT_VALUE'FME_NULL_VALUE'BOOL_OP;OR;COMPOSITE_TEST;1;TEST height ATTRIBUTE_HAS_A_VALUE _FME_BLANK_STRING_'@Value(height)'BOOL_OP;OR;COMPOSITE_TEST;1;TEST ds_height ATTRIBUTE_HAS_A_VALUE _FME_BLANK_STRING_'@Value(ds_height)'FME_NUM_CONDITIONS3___
    -> AttributeKeeper
AttributeKeeper
    CREATE_BULK_MODE_FEATURES = NO
    KEEP_ATTRS = system_type,asset_id,ds_node_id,height,link_suffix,shape1,us_node_id,width,ds_invert,us_invert,solution_model,material,uid,year_laid
    -> AttributeManager
AttributeManager
    ATTR_TABLE:
      RENAME_SET_VALUE link_suffix > suffix
      RENAME_SET_VALUE system_type > type
      SET_TO sewer_ref
      RENAME_SET_VALUE shape1 > shape
      RENAME_SET_VALUE solution_model > solution
      RENAME_SET_VALUE year_laid > year = @Left(@Value(year),4)
    USER_EXPOSED_ATTRIBUTES = OID
    -> Junction_5
Junction_5
    -> Junction_6
