FME workspace A iexchange.fmw

Bookmark: list: of system command requests
Creator
    GEOMTYPE = Geometry Object
    NUM = 1
    CREATED -> _pipes
_pipes: AttributeCreator
    ATTR_TABLE:
      SET_TO _iexchange = C:\Program Files (x86)\Innovyze Workgroup Client 2021.8\iexchange.exe
      SET_TO _script = $(FME_MF_DIR_ENCODED)backend\ie_in_pipes_gdb_export.rb
      SET_TO _gdb_file = $(FME_MF_DIR_ENCODED)exports\pipes
      SET_TO system_cmd = ""@Value(_iexchange)" "@Value(_script)" /IA"
    -> Junction
Creator_2
    GEOMTYPE = Geometry Object
    NUM = 1
    CREATED -> zone
zone: AttributeCreator
    ATTR_TABLE:
      SET_TO _iexchange = C:\Program Files (x86)\Innovyze Workgroup Client 2021.8\iexchange.exe
      SET_TO _script = $(FME_MF_DIR_ENCODED)backend\ie_in_zone_gdb_export.rb
      SET_TO _gdb_file = $(FME_MF_DIR_ENCODED)exports\zone
      SET_TO system_cmd = ""@Value(_iexchange)" "@Value(_script)" /IA"
    -> Junction
Junction
    -> Junction_2

Bookmark: system command: run ruby script to extract latest pipes
Junction_2
    -> _del_folder
_del_folder: SystemCaller
    ATTR = _exit_code_a
    CMD = if exist "@Value(_gdb_file)" (rmdir /s/q "@Value(_gdb_file)")
    -> Tester_3
Tester_3
    BOOL_OP = OR
    TEST_CLAUSE = TEST @Value(_exit_code_a) = 0
    TEST_MODE = TEST
    PASSED -> _mkdir
_mkdir: SystemCaller
    ATTR = _exit_code_c
    CMD = mkdir "@Value(_gdb_file)"
    -> Tester_4
Tester_4
    BOOL_OP = OR
    TEST_CLAUSE = TEST @Value(_exit_code_c) = 0
    TEST_MODE = TEST
    PASSED -> _create_gdb
_create_gdb: SystemCaller
    ATTR = _exit_code_b
    CMD = @Value(system_cmd)
    -> Tester_2
Tester_2
    BOOL_OP = OR
    TEST_CLAUSE = TEST @Value(_exit_code_b) = 0
    TEST_MODE = TEST
