FME workspace B statistics.fmw

Parameters:
- DestDataset_GEOJSON = $(FME_MF_DIR)exports\dma_stats.json   # Destination GeoJSON File
- SourceDataset_XLSXR = $(FME_MF_DIR)excel\input.xlsm   # Source Microsoft Excel File(s)
- DestDataset_REDSHIFT = AmazonRedshiftDW   # Connection
- SourceDataset_GEOJSON = $(FME_MF_DIR)gis\til_address_property_category.zip   # Source GeoJSON File or URL
- SourceDataset_FILEGDB_3 = $(FME_MF_DIR)exports\zone\ZONES.gdb   # File Geodatabase
- SourceDataset_FILEGDB = $(FME_MF_DIR)exports\pipes\*.gdb   # File Geodatabase

Readers:
- GEOJSON_1: GEOJSON from $(SourceDataset_GEOJSON)
- FILEGDB_1: FILEGDB from $(SourceDataset_FILEGDB)
- FILEGDB_2: FILEGDB from $(SourceDataset_FILEGDB_3)
- XLSXR_1: XLSXR from $(SourceDataset_XLSXR)

Writers:
- GEOJSON_2: GEOJSON to $(DestDataset_GEOJSON) in EPSG:4326
- REDSHIFT_2: REDSHIFT to $(DestDataset_REDSHIFT)

Bookmark: extract: zone data from iexchange dump
_/__Zone (reader FILEGDB_2)
    attributes: OID objectid, area_renamed double, category_id text(40), mobile_uid text(100), polygon_id text(40), uid text(32), user_date_1 date, user_date_2 date, user_date_3 date, user_date_4 date, user_date_5 date, user_number_1 double, user_number_10 double, user_number_11 double, user_number_12 double, user_number_13 double, user_number_14 double, user_number_15 double, user_number_16 double, user_number_17 double, user_number_18 double, user_number_19 double, user_number_2 double, user_number_20 double, user_number_21 double, user_number_22 double, user_number_23 double, user_number_24 double, user_number_25 double, user_number_26 double,
      user_number_27 double, user_number_28 double, user_number_29 double, user_number_3 double, user_number_30 double, user_number_31 double, user_number_32 double, user_number_33 double, user_number_34 double, user_number_35 double, user_number_36 double, user_number_37 double, user_number_38 double, user_number_39 double, user_number_4 double, user_number_40 double, user_number_5 double, user_number_6 double, user_number_7 double, user_number_8 double, user_number_9 double, user_text_1 text(250), user_text_10 text(250), user_text_11 text(250), user_text_12 text(250), user_text_13 text(250), user_text_14 text(250), user_text_15 text(250), user_text_16 text(250), user_text_17 text(250),
      user_text_18 text(250), user_text_19 text(250), user_text_2 text(250), user_text_20 text(250), user_text_21 text(250), user_text_22 text(250), user_text_23 text(250), user_text_24 text(250), user_text_25 text(250), user_text_26 text(250), user_text_27 text(250), user_text_28 text(250), user_text_29 text(250), user_text_3 text(250), user_text_30 text(250), user_text_31 text(250), user_text_32 text(250), user_text_33 text(250), user_text_34 text(250), user_text_35 text(250), user_text_36 text(250), user_text_37 text(250), user_text_38 text(250), user_text_39 text(250), user_text_4 text(250), user_text_40 text(250), user_text_5 text(250), user_text_6 text(250), user_text_7 text(250), user_text_8 text(250),
      user_text_9 text(250), hotlinks text(100), FGeom_Length double, FGeom_Area double
    -> Reprojector
Reprojector
    DEST = EPSG:4326
    INTERPOLATION_TYPE_NAME = Nearest Neighbor
    RASTER_CELL_SIZE = Preserve Cells
    RASTER_TOLERANCE = 0.0
    REPROJECTED -> TestFilter
TestFilter
    DEFAULT_VALUE = <UNFILTERED>
    PASSED_TEST_GROUP_OUTPUT = FIRST
    TEST_LIST = "BOOL_OP,OR,COMPOSITE_TEST,""""""1"""""",TEST_CLAUSE,CASE_INSENSITIVE_TEST @Value(category_id) != pressure",not-pressure,"BOOL_OP,AND,COMPOSITE_TEST,""""""1"""""",TEST_CLAUSE,CASE_INSENSITIVE_TEST @Value(user_text_17) = in-active",in-active,"BOOL_OP,OR,COMPOSITE_TEST,""""""1"""""",TEST_CLAUSE,CASE_INSENSITIVE_TEST @Value(user_text_1) CONTAINS future",future
    <UNFILTERED> -> AttributeKeeper
AttributeKeeper
    CREATE_BULK_MODE_FEATURES = NO
    KEEP_ATTRS = OID,polygon_id,uid,user_text_1,user_text_17,user_date_1,user_text_6,user_text_5
    -> AttributeRenamer
AttributeRenamer
    ATTR_TABLE:
      RENAME_SET_DEFAULT user_date_1 > update_date
      RENAME_SET_DEFAULT user_text_1 > name
      RENAME_SET_DEFAULT user_text_17 > status
    MISSING_INPUT_ATTRS = REMOVE
    -> AttributeManager
AttributeManager
    ATTR_TABLE:
      RENAME_SET_VALUE user_text_5 > council
      RENAME_SET_VALUE user_text_6 > wsa
    USER_EXPOSED_ATTRIBUTES = user_text_7
    -> Junction_4
    -> Junction_7
    -> Junction_9
Junction_4
    -> Junction_5
Junction_7
    -> Junction_8
Junction_9
    -> Junction_10

Bookmark: transform: filter on active pipes and locate within DMAs
Junction_5
    -> LineOnAreaOverlayer [AREA]
Junction_2
    -> _owner
_owner: Tester
    BOOL_OP = OR
    TEST_CLAUSE:
      TEST @Value(owner) = WCC
      TEST @Value(owner) = PCC
      TEST @Value(owner) = UHCC
      TEST @Value(owner) = UHC
      TEST @Value(owner) = HCC
      TEST @Value(owner) = SWDC
    TEST_MODE = TEST
    PASSED -> _type
_type: Tester
    BOOL_OP = OR
    TEST_CLAUSE:
      TEST @Value(type) = MAIN
      TEST @Value(type) = RIDE
      TEST @Value(type) = FIRE
      TEST @Value(type) = TRAN
    TEST_MODE = TEST
    PASSED -> _status
_status: Tester
    BOOL_OP = OR
    TEST_CLAUSE:
      TEST @Value(status) = INUS
      TEST @Value(status) = INUSE
    TEST_MODE = TEST
    PASSED -> AttributeValueMapper
AttributeValueMapper
    DEFAULT_VALUE = rigid
    LUT = MDPE,flexible,MPVC,flexible,OPVC,flexible,PE,flexible,PE100,flexible,PE80,flexible,PVC,flexible,UPVC,flexible,ABS,flexible,BUTYL,flexible,uPVC,flexible,DUX QUEST,flexible,PE80b,flexible,mPVC,flexible,PE80B,flexible,MDPE,flexible
    MAPPING_DIRECTION = FORWARD
    SRC = material
    VAL_ATTR = material_n1c
    -> LineOnAreaOverlayer [LINE]
LineOnAreaOverlayer
    CLEANING_TOLERANCE = Automatic
    DEAGGREGATE_INPUT = Yes
    LIST_ATTRS_TO_INCLUDE = polygon_id
    LIST_NAME = _list
    OV_ATTR = _overlaps
    LINE -> AttributeCreator_2
AttributeCreator_2
    ATTR_TABLE:
      SET_TO polygon_id = @Value(_list{0}.polygon_id)
      SET_TO age = FME_CONDITIONAL:DEFAULT_VALUE'@DateTimeDiff(@DateTimeNow(),@DateTimeFormat(@Value(date_installed),%Y%m%d000000),Years)'BOOL_OP;OR;COMPOSITE_TEST;1;TEST @Value(date_installed) = 000000'FME_NULL_VALUE'BOOL_OP;OR;COMPOSITE_TEST;1;TEST date_installed ATTRIBUTE_VALUE_NULL _FME_BLANK_STRING_'FME_NULL_VALUE'FME_NUM_CONDITIONS3___
    -> StatisticsCalculator_4
StatisticsCalculator_4
    CALCULATION_MODE = NUMERIC
    FEAT_STATS = length,NUMERIC_MODE,,,,SUM,,,,,,,,,
    GROUP_BY = polygon_id
    COMPLETE -> Junction_11
Junction_11
    -> Junction_12

Bookmark: tansform: locate address points within DMAs
Junction_8
    -> PointOnAreaOverlayer_2 [AREA]
Junction_6
    -> PointOnAreaOverlayer_2 [POINT]
PointOnAreaOverlayer_2
    ATTR_ACCUM_MODE = Merge Incoming
    ATTR_CONFLICT_RES = Use Original
    DEAGGREGATE_INPUT = Yes
    OV_ATTR = _overlaps
    POLYS_FIRST = NO
    POINT -> Tester_MULTIoverlap
Note: target passed < 100
Tester_MULTIoverlap
    BOOL_OP = OR
    TEST_CLAUSE = TEST @Value(_overlaps) > 1
    TEST_MODE = TEST
    PASSED -> Tester_overlap
    FAILED -> Tester_overlap
Tester_overlap
    BOOL_OP = OR
    TEST_CLAUSE = TEST @Value(_overlaps) >= 1
    TEST_MODE = TEST
    PASSED -> AttributeCreator
AttributeCreator
    ATTR_TABLE:
      SET_TO Address = @Value(FULL_ADDRESS) @Value(FULL_PRIMARY_ROAD_NAME) @Value(LOCALITY_NAME)
      SET_TO address_pt = FME_CONDITIONAL:DEFAULT_VALUE'add_pt'BOOL_OP;OR;COMPOSITE_TEST;1;CASE_INSENSITIVE_TEST @Value(IN_USE_TYPE) CONTAINS Alias'not an add_pt'FME_NUM_CONDITIONS2___
      SET_TO user = FME_CONDITIONAL:DEFAULT_VALUE'not a user'BOOL_OP;AND;COMPOSITE_TEST;1 AND 2 AND 3;TEST @Value(address_pt) = add_pt;TEST @Value(SECO_CAT) NOT_CONTAINS Vacant;TEST @Value(IN_USE_TYPE) NOT_CONTAINS Unused'user'FME_NUM_CONDITIONS2___
      SET_TO park = FME_CONDITIONAL:DEFAULT_VALUE'not a park'BOOL_OP;OR;COMPOSITE_TEST;1 OR 2;CASE_INSENSITIVE_TEST @Value(IN_USE_TYPE) CONTAINS Park;CASE_INSENSITIVE_TEST @Value(SECO_CAT) CONTAINS Passive Reserve'park'FME_NUM_CONDITIONS2___
      SET_TO residential = FME_CONDITIONAL:DEFAULT_VALUE'non-residential'BOOL_OP;OR;COMPOSITE_TEST;1 OR 2 OR 3;NUM_TEST @Value(PRIM_CAT) = Residential;TEST @Value(PRIM_CAT) = Lifestyle;TEST @Value(MATCH_TYPE_2) = Residential mixed'residential'FME_NUM_CONDITIONS2___
      SET_TO PRIM_CAT_G = FME_CONDITIONAL:DEFAULT_VALUE'@Value(PRIM_CAT)'BOOL_OP;OR;COMPOSITE_TEST;1 OR 2 OR 3 OR 4 OR 5;TEST @Value(PRIM_CAT) = Pastoral;TEST @Value(PRIM_CAT) = Dairying;TEST @Value(PRIM_CAT) = Horticulture;TEST @Value(PRIM_CAT) = Forestry;TEST @Value(PRIM_CAT) = Mining'Primary sector'BOOL_OP;OR;COMPOSITE_TEST;1 OR 2 OR 3 OR 4;TEST PRIM_CAT ATTRIBUTE_IS_EMPTY _FME_BLANK_STRING_;TEST PRIM_CAT ATTRIBUTE_IS_MISSING _FME_BLANK_STRING_;TEST @Value(PRIM_CAT) = Other;TEST PRIM_CAT ATTRIBUTE_VALUE_NULL _FME_BLANK_STRING_'Unknown'FME_NUM_CONDITIONS3___
      SET_TO SAM_CAT = FME_CONDITIONAL:DEFAULT_VALUE'FME_NULL_VALUE'BOOL_OP;OR;COMPOSITE_TEST;1 OR 2 OR 3;TEST @Value(CATEGORY_GROUP) = RD;TEST @Value(CATEGORY_GROUP) = RA;TEST @Value(CATEGORY_GROUP) = RH'@Value(CATEGORY_GROUP)'BOOL_OP;OR;COMPOSITE_TEST;1 OR 2 OR 3;TEST @Value(CATEGORY_GROUP) = RC;TEST @Value(CATEGORY_GROUP) = RF;TEST @Value(CATEGORY_GROUP) = RR'RC_RF_RR'FME_NUM_CONDITIONS3___
      SET_TO ph_conn = @Value(HOUSE_HIGH) @Value(FULL_PRIMARY_ROAD_NAME) @Value(LOCALITY_NAME) @Value(residential) @Value(polygon_id)
      SET_TO ta_conn = FME_CONDITIONAL:DEFAULT_VALUE'_FME_NO_OP_'BOOL_OP;OR;COMPOSITE_TEST;1;TEST @Value(user) = not a user'FME_NULL_VALUE'BOOL_OP;AND;COMPOSITE_TEST;1 AND 2;TEST @Value(user) = user;TEST @Value(residential) = residential'@Value(ID)'BOOL_OP;AND;COMPOSITE_TEST;1 AND 2;TEST @Value(user) = user;TEST @Value(residential) = non-residential'@Value(ph_conn)'FME_NUM_CONDITIONS4___
      SET_TO cl_fhc = FME_CONDITIONAL:DEFAULT_VALUE'FME_NULL_VALUE'BOOL_OP;OR;COMPOSITE_TEST;1 OR 2 OR 3 OR 4 OR 5;TEST @Value(MAX_FIRE_HAZARD) = 1;TEST @Value(MAX_FIRE_HAZARD) = 2;TEST @Value(MAX_FIRE_HAZARD) = 3;TEST @Value(MAX_FIRE_HAZARD) = 4;TEST @Value(MAX_FIRE_HAZARD) = 5'@Value(MAX_FIRE_HAZARD)'FME_NUM_CONDITIONS2___
      SET_TO cl_sprinkl = FME_CONDITIONAL:DEFAULT_VALUE'sprinkler'BOOL_OP;OR;COMPOSITE_TEST;1 OR 2;TEST SYSTEM_NAME ATTRIBUTE_VALUE_NULL _FME_BLANK_STRING_;TEST SYSTEM_NAME ATTRIBUTE_IS_MISSING _FME_BLANK_STRING_'no sprinkler'FME_NUM_CONDITIONS2___
    -> AttributeRenamer_3
AttributeRenamer_3
    ATTR_TABLE:
      RENAME_SET_DEFAULT FULL_ADDRESS > AddressNo
      RENAME_SET_DEFAULT FULL_PRIMARY_ROAD_NAME > AddressSt
      RENAME_SET_DEFAULT LOCALITY_NAME > AddressLoc
      RENAME_SET_DEFAULT IN_USE_TYPE > IN_USE_T
      RENAME_SET_DEFAULT LEVELS_ESTIMATED > cl_levels
      RENAME_SET_DEFAULT BEDROOMS > cl_bed
      RENAME_SET_DEFAULT BATHROOMS > cl_bath
      RENAME_SET_DEFAULT BUILDING_AGE > bdg_age
      RENAME_SET_DEFAULT BUILDING_FLOOR_AREA > floor_area
      RENAME_SET_DEFAULT BUILDING_SITE_COVER > roof_area
      RENAME_SET_DEFAULT LAND_AREA > land_area
    MISSING_INPUT_ATTRS = REMOVE
    -> Tester
    -> Tester_2
Tester_2
    BOOL_OP = OR
    TEST_CLAUSE = TEST @Value(address_pt) = add_pt
    TEST_MODE = TEST
    PASSED -> _address_pts
_address_pts: StatisticsCalculator [off]
    CALCULATION_MODE = LEXICAL
    FEAT_STATS = ph_conn,LEXICAL,,,COUNT,<Unused>,<Unused>,,,<Unused>,<Unused>,<Unused>,,
    GROUP_BY = ph_conn
    COMPLETE -> Inspector
Inspector [off]
Tester
    BOOL_OP = OR
    TEST_CLAUSE = TEST @Value(user) = user
    TEST_MODE = TEST
    PASSED -> _water_users
    PASSED -> _users
_water_users: StatisticsCalculator [off]
    CALCULATION_MODE = LEXICAL
    FEAT_STATS = ph_conn,LEXICAL,,,COUNT,<Unused>,<Unused>,,,<Unused>,<Unused>,<Unused>,,
    GROUP_BY = ph_conn
    COMPLETE -> Inspector_2
Inspector_2 [off]
_users: StatisticsCalculator
    CALCULATION_MODE = NUMERIC
    FEAT_STATS = polygon_id,NUMERIC_MODE,,,COUNT,,,,,,,,,
    GROUP_BY = polygon_id residential ta_conn
    SUMMARY -> Junction_13
Junction_13
    -> Junction_14

Bookmark: table: prep table for loading
Junction_10
    -> InlineQuerier [dma]
Junction_12
    -> InlineQuerier [pipes]
Junction_18
    -> InlineQuerier [pressure]
Junction_14
    -> InlineQuerier [users]
InlineQuerier
    QUERY_DEF:
      results,WITH tbl_users AS (SELECT * FROM users)
      , tbl_pipes AS (SELECT * FROM pipes)
      , tbl_dma AS (SELECT * FROM dma)
      , tbl_pressure AS (SELECT * FROM pressure)

      , qry_users_res AS (
          SELECT polygon_id, Count(*) AS count_res
          FROM tbl_users
          WHERE residential = 'residential'
          GROUP BY polygon_id
      ) --SELECT * FROM qry_users_res

      , qry_users_com AS (
          SELECT polygon_id, Count(*) AS count_com
          FROM tbl_users
          WHERE residential = 'non-residential'
          GROUP BY polygon_id
      ) --SELECT * FROM qry_users_com

      , qry_rigid AS (
          SELECT polygon_id, SUM(length) AS lm_rigid
          FROM tbl_pipes
          WHERE material_n1c = 'rigid'
      	AND polygon_id is not null
          GROUP BY polygon_id
      ) -- SELECT * FROM qry_rigid

      , qry_flexible AS (
          SELECT polygon_id, SUM(length) AS lm_flexible
          FROM tbl_pipes
          WHERE material_n1c = 'flexible'
      	AND polygon_id is not null
          GROUP BY polygon_id
      ) -- SELECT * FROM qry_flexible

      , qry_age AS (
          SELECT polygon_id, AVG(age) AS age_avg
          FROM tbl_pipes
          WHERE polygon_id is not null
          GROUP BY polygon_id
      ) -- SELECT * FROM qry_age

      SELECT * FROM tbl_dma AS d
      LEFT JOIN qry_users_res AS cr ON d.polygon_id = cr.polygon_id
      LEFT JOIN qry_users_com AS cc ON d.polygon_id = cc.polygon_id
      LEFT JOIN qry_rigid AS r ON d.polygon_id = r.polygon_id
      LEFT JOIN qry_flexible AS f ON d.polygon_id = f.polygon_id
      LEFT JOIN qry_age AS a ON d.polygon_id = a.polygon_id
      LEFT JOIN tbl_pressure AS p ON d.polygon_id = p.polygon_id,FIRST
    QUERY_SCHEMA = results,OID,integer,uid,varchar(32),council,varchar(250),wsa,varchar(250),polygon_id,varchar(40),name,varchar(250),status,varchar(250),update_date,text,dma.fme_feature_content,fme_feature_content,count_res,,count_com,,lm_rigid,,lm_flexible,,age_avg,,avgp,integer,avg_np,integer,pressure.fme_feature_content,fme_feature_content
    TABLE_DEF = dma,OID,integer,uid,varchar(32),council,varchar(250),wsa,varchar(250),polygon_id,varchar(40),name,varchar(250),status,varchar(250),update_date,text,users,residential,varchar(200),ta_conn,varchar(200),polygon_id,varchar(40),polygon_id.total_count,varchar(20),pipes,polygon_id,varchar(200),age,varchar(200),status,varchar(20),condition_survey_date,text,structural_condition_grade,integer,expected_lifetime,integer,replacement_cost,double,use,varchar(10),depth,double,width,varchar(200),height,varchar(200),shape,varchar(200),invert,varchar(200),service_condition_grade,varchar(200),x_coord,varchar(200),y_coord,varchar(200),area_code,varchar(40),asset_id,varchar(40),current_value,double,date_installed,text,length,double,lining_material,varchar(10),location,varchar(100),material,varchar(10),owner,varchar(64),pipe_class,varchar(64),type,varchar(10),uid,varchar(32),material_n1c,text,_overlaps,integer,length.sum,double,pressure,polygon_id,varchar(14),avgp,integer,avg_np,integer
    results -> NullAttributeMapper
NullAttributeMapper
    ATTRCHOICE = Selected Attributes
    ATTRLIST = count_com count_res lm_flexible lm_rigid
    NEW_VALUE = 0
    NULL_TREATMENT = New Value
    SOURCE_ATTR_VAL = Null
    -> NullAttributeMapper_2
NullAttributeMapper_2
    ATTRCHOICE = Selected Attributes
    ATTRLIST = age_avg
    NEW_VALUE = 50
    NULL_TREATMENT = New Value
    SOURCE_ATTR_VAL = Null
    -> AttributeCreator_4
Note: AttributeCreator_4 [AttributeCreator] / Attributes To Create: New AttributeAttribute Valuelm@double((@Value(lm_flexible)+@Value(lm_rigid)))n1c@round(1.5-(1-0.65/2.1)*((@Value(lm_rigid)/1000)/((@Value(lm_flexible)/1000)+(@Value(lm_rigid)/1000))),3)avgp<2 Possible Values>avg_np<2 Possible Values>fdn@round(@pow((@Value(avgp)/@Value(avg_np)),@Value(n1c)),3)nc@int(@Value(count_com)+@Value(count_res))
AttributeCreator_4
    ATTR_TABLE:
      SET_TO lm = @double((@Value(lm_flexible)+@Value(lm_rigid)))
      SET_TO n1c = @round(1.5-(1-0.65/2.1)*((@Value(lm_rigid)/1000)/((@Value(lm_flexible)/1000)+(@Value(lm_rigid)/1000))),3)
      SET_TO avgp = FME_CONDITIONAL:DEFAULT_VALUE'70'BOOL_OP;OR;COMPOSITE_TEST;1;TEST avgp ATTRIBUTE_HAS_A_VALUE _FME_BLANK_STRING_'@Value(avgp)'FME_NUM_CONDITIONS2___
      SET_TO avg_np = FME_CONDITIONAL:DEFAULT_VALUE'75'BOOL_OP;OR;COMPOSITE_TEST;1;TEST avg_np ATTRIBUTE_HAS_A_VALUE _FME_BLANK_STRING_'@Value(avg_np)'FME_NUM_CONDITIONS2___
      SET_TO fdn = @round(@pow((@Value(avgp)/@Value(avg_np)),@Value(n1c)),3)
      SET_TO nc = @int(@Value(count_com)+@Value(count_res))
    -> AttributeRenamer_4
AttributeRenamer_4
    ATTR_TABLE = RENAME_SET_DEFAULT polygon_id > zone_id
    MISSING_INPUT_ATTRS = REMOVE
    -> AttributeRounder
AttributeRounder
    PLACES = 0
    ROUND_TYPE = Nearest
    SRC_ATTRS = age_avg lm lm_flexible lm_rigid
    -> AttributeRounder_2
AttributeRounder_2
    PLACES = 3
    ROUND_TYPE = Nearest
    SRC_ATTRS = n1c
    -> Junction_15
Junction_15
    -> Junction_16

Bookmark: extract: pipe data from iexchange dump
_/__Pipe (reader FILEGDB_1)
    attributes: OID objectid, object_id text(83), access_restrictions text(64), area_code text(40), asset_id text(40), barcode text(255), bedding_material text(10), capacity double, condition_grade int, consequence_comments text(255), consequence_score double, construction_method text(10), criticality text(5), criticality_score double, cum_sediment text(10), current_value double, date_cleaned date, date_installed date, date_lined date, date_renewed date, depth_of_cover double, ds_node_id text(40), external_diameter double, external_protection text(10), external_protection_date date, flow_reversals text(10), friction_factor double, gps_survey_date date, headloss double, id_renamed text(40),
      inspection_cost double, install_cost double, internal_diameter double, joint_type text(10), leakage double, length double, lifetime int, likelihood_score double, lining_material text(10), lining_type text(10), location text(100), manufacturer text(20), material text(10), max_velocity double, min_velocity double, mobile_uid text(100), nominal_diameter double, operational_status text(20), owner text(64), photo text(50), photo_filename text(255), photo_ref text(30), pipe_class text(64), planning_status text(20), pressure_rating double, rail_business_disruption_risk double, rehab_cost double, rehab_method text(10), replace_cost double, risk_score double,
      security text(10), sketch text(50), sketch_filename text(255), sketch_ref text(30), soil_type text(10), surface_type text(10), survey_date date, traffic_level double, type text(10), uid text(32), us_node_id text(40), use_renamed text(10), user_date_1 date, user_date_2 date, user_date_3 date, user_date_4 date, user_date_5 date, user_number_1 double, user_number_10 double, user_number_11 double, user_number_12 double, user_number_13 double, user_number_14 double, user_number_15 double, user_number_16 double, user_number_17 double, user_number_18 double, user_number_19 double, user_number_2 double, user_number_20 double,
      user_number_21 double, user_number_22 double, user_number_23 double, user_number_24 double, user_number_25 double, user_number_26 double, user_number_27 double, user_number_28 double, user_number_29 double, user_number_3 double, user_number_30 double, user_number_31 double, user_number_32 double, user_number_33 double, user_number_34 double, user_number_35 double, user_number_36 double, user_number_37 double, user_number_38 double, user_number_39 double, user_number_4 double, user_number_40 double, user_number_5 double, user_number_6 double, user_number_7 double, user_number_8 double, user_number_9 double, user_text_1 text(250), user_text_10 text(250), user_text_11 text(250),
      user_text_12 text(250), user_text_13 text(250), user_text_14 text(250), user_text_15 text(250), user_text_16 text(250), user_text_17 text(250), user_text_18 text(250), user_text_19 text(250), user_text_2 text(250), user_text_20 text(250), user_text_21 text(250), user_text_22 text(250), user_text_23 text(250), user_text_24 text(250), user_text_25 text(250), user_text_26 text(250), user_text_27 text(250), user_text_28 text(250), user_text_29 text(250), user_text_3 text(250), user_text_30 text(250), user_text_31 text(250), user_text_32 text(250), user_text_33 text(250), user_text_34 text(250), user_text_35 text(250), user_text_36 text(250), user_text_37 text(250), user_text_38 text(250), user_text_39 text(250),
      user_text_4 text(250), user_text_40 text(250), user_text_5 text(250), user_text_6 text(250), user_text_7 text(250), user_text_8 text(250), user_text_9 text(250), hotlinks text(100), FGeom_Length double
    -> Reprojector_3
Reprojector_3
    DEST = EPSG:4326
    INTERPOLATION_TYPE_NAME = Nearest Neighbor
    RASTER_CELL_SIZE = Preserve Cells
    RASTER_TOLERANCE = 0.0
    REPROJECTED -> CoordinateExtractor
CoordinateExtractor
    LIST_NAME = _indices
    MODE = All Coordinates
    -> AttributeCreator_3
AttributeCreator_3
    ATTR_TABLE:
      SET_TO width = FME_CONDITIONAL:DEFAULT_VALUE'FME_NULL_VALUE'BOOL_OP;OR;COMPOSITE_TEST;1;TEST @Value(nominal_diameter) > 0'@Value(nominal_diameter)'BOOL_OP;OR;COMPOSITE_TEST;1;TEST @Value(internal_diameter) > 0'@Value(internal_diameter)'BOOL_OP;OR;COMPOSITE_TEST;1;TEST @Value(external_diameter) > 0'@Value(external_diameter)'FME_NUM_CONDITIONS4___
      SET_TO height = @Value(width)
      SET_TO shape = CIRC
      SET_TO invert = FME_NULL_VALUE
      SET_TO service_condition_grade = FME_NULL_VALUE
      SET_TO x_coord = @Value(_indices{0}.x)
      SET_TO y_coord = @Value(_indices{0}.y)
    -> AttributeRenamer_2
AttributeRenamer_2
    ATTR_TABLE:
      RENAME_SET_DEFAULT operational_status > status
      RENAME_SET_DEFAULT survey_date > condition_survey_date
      RENAME_SET_DEFAULT condition_grade > structural_condition_grade
      RENAME_SET_DEFAULT lifetime > expected_lifetime
      RENAME_SET_DEFAULT replace_cost > replacement_cost
      RENAME_SET_DEFAULT use_renamed > use
      RENAME_SET_DEFAULT depth_of_cover > depth
    MISSING_INPUT_ATTRS = REMOVE
    -> AttributeKeeper_2
AttributeKeeper_2
    CREATE_BULK_MODE_FEATURES = NO
    KEEP_ATTRS = area_code,asset_id,location,owner,status,uid,use,type,length,width,height,shape,date_installed,material,lining_material,pipe_class,invert,depth,condition_survey_date,structural_condition_grade,service_condition_grade,expected_lifetime,current_value,replacement_cost,x_coord,y_coord
    -> Junction
Junction
    -> Junction_2

Bookmark: extract: pressure data
wz_dma (reader XLSXR_1)
    attributes: zone_id char(14), dma_name char(25), category_id char(9), land_use_type char(12), ell_zone_id char(14), water_supply_zone char(35), region char(3), council char(5), status char(10), ili_band char(10), pipe_age number(3,0), avgp number(4,0), avg_np number(4,0), timep number(2,0), leaker number(4,2), leaker_com number(4,2), icf number(3,1), fdn number(6,3), gres number(4,0), gcom number(5,0), unauthorised_consumption_perc number(5,3), lnus number(3,1), carl_type char(7), flexible_km_lm number(6,3), regid_km_lm number(6,3), n1c number(5,3), lm number(6,0), nc number(5,0), nc_res number(5,0), pop number(6,0),
      nm_r number(2,0), nm_nr number(4,0), nu_r number(5,0), nu_nr number(5,0), rm_repairs_perc number(4,2), avgq_service_repairs number(3,1), avgq_main_repairs number(3,0), unreported_public_bursts_perc number(4,2), unreported_service_bursts_perc number(4,2), cost_water_cv number(3,1), leak_mangt_cost number(4,0), ci_lm number(4,2), ci_nc number(4,2), ci_avgp number(4,2), ci_wi number(4,2), ci_we number(4,2), ci_bmcn number(4,2), ci_bumc number(4,2), ci_burp number(4,2), ci_wlcn number(3,1), ci_wlrp number(3,1)
    -> AttributeKeeper_3
AttributeKeeper_3
    CREATE_BULK_MODE_FEATURES = NO
    KEEP_ATTRS = avg_np,avgp,zone_id
    -> AttributeRenamer_5
AttributeRenamer_5
    ATTR_TABLE = RENAME_SET_DEFAULT zone_id > polygon_id
    MISSING_INPUT_ATTRS = REMOVE
    -> Junction_17
Junction_17
    -> Junction_18

Bookmark: extract: latest core logic address points
til_address_property_category (reader GEOJSON_1)
    attributes: OBJECTID int, ID int, TUI int, CREATED_DATE string, ALPHA_MODIFIED_DATE string, GEOM_MODIFIED_DATE string, UNIT_TYPE string, FLAT_LOW string, HOUSE_LOW int, HOUSE_LOW_SUFFIX string, FLAT_HIGH string, HOUSE_HIGH int, HOUSE_HIGH_SUFFIX string, LOCALITY_ID int, LOCALITY_NAME string, TOWN_NAME string, TA_NAME string, POSTCODE string, IN_USE_TYPE string, ADDRESS_TYPE string, ADDRESS_FORMAT string, LEVEL_TYPE string, LEVEL_NO int, RD_SEG_SIDE string, FULL_ADDRESS string, RD_SEG_ID int, FULL_PRIMARY_ROAD_NAME string, PRIMARY_ROAD_NAME string, PRIMARY_ROAD_SUFFIX string, PRIMARY_ROAD_TYPE string,
      ALTERNATE_ROAD_NAME string, HABITATION_NAME string, NZTM_X float, NZTM_Y float, PARCEL_ID int, PARCEL_INTENT string, PARCEL_CATEGORY string, MATCH_TYPE_1 string, MATCH_TYPE_2 string, QPID int, CATEGORY_CODE string, CATEGORY_DESC string, CATEGORY_GROUP string, PRIM_CAT string, SECO_CAT string, TERT_CAT string, APPORTIONMENTS string, BATHROOMS int, BEDROOMS int, BUILDING_AGE int, BUILDING_FLOOR_AREA int, BUILDING_SITE_COVER int, LAND_AREA float, LEVELS_ESTIMATED int, UNITS_OF_USE int, LAND_USE_ID int, LAND_USE string, CAT_LIST string, COM_VAL int, RES_VAL int,
      OTHER_VAL int, VAL_COUNT int, TUI_COUNT int, TUI_ALIAS_COUNT int, TUI_PRIMARY_COUNT int, MAX_FIRE_HAZARD string, SYSTEM_NAME string
    -> Reprojector_2
Reprojector_2
    DEST = EPSG:4326
    INTERPOLATION_TYPE_NAME = Nearest Neighbor
    RASTER_CELL_SIZE = Preserve Cells
    RASTER_TOLERANCE = 0.0
    REPROJECTED -> Junction_3
Junction_3
    -> Junction_6

Bookmark: load: 2DWh
Junction_16
    -> AttributeManager_2
AttributeManager_2
    ATTR_TABLE:
      RENAME_SET_VALUE name > dma_name
      SET_TO category_id = pressure
      SET_TO ell_zone_id = FME_NULL_VALUE
      RENAME_SET_VALUE count_res > nc_res
      RENAME_SET_VALUE age_avg > pipe_age
      REMOVE OID
      REMOVE uid
      REMOVE wsa
      REMOVE status
      REMOVE count_com
      REMOVE lm_rigid
      REMOVE lm_flexible
      REMOVE avg_np
      REMOVE update_date
    -> wz_dma (writer REDSHIFT_2)
wz_dma (writer REDSHIFT_2) [off]
    attributes: zone_id varchar(20), dma_name varchar(100), category_id varchar(20), ell_zone_id varchar(20), council varchar(10), avgp int2, fdn float4, lm float4, nc int8, nc_res int8, n1c float4, pipe_age int4
