FME workspace features.fmw

Bookmark: extract: scheme boundaries
Creator
    GEOMTYPE = Geometry Object
    NUM = 1
    CREATED -> FeatureReader [INITIATOR]
FeatureReader
    ARCGISONLINEFEATURES_CREATE_FEATURE_TABLES_FROM_DATA = Yes
    ARCGISONLINEFEATURES_FEATURESERVICE = Queenstown Lakes District Council Open Data/Three Waters Schemes(c2b563e7c41f44a6ad5d04efd337d118)
    ARCGISONLINEFEATURES_FEATURES_PER_REQUEST = 1000
    ARCGISONLINEFEATURES_FORMAT_GUID = YES
    ARCGISONLINEFEATURES_NC = hywell Esri ArcGIS Online
    ARCGISONLINEFEATURES_QUERY_FEATURE_TYPES_FOR_MERGE_FILTERS = Yes
    ARCGISONLINEFEATURES_RESOLVE_DOMAINS = No
    ARCGISONLINEFEATURES_TABLELIST = "Scheme Boundaries"
    ARCGISONLINEFEATURES_USE_SEARCH_ENVELOPE = NO
    ATTRIBUTES = "Scheme Boundaries","OBJECTID,WaterType,Name,Ownership,Delivery,Maintenance,DecisionDate,VolumeRestrictions,Notes,GlobalID,created_user,created_date,last_edited_user,last_edited_date,Shape__Area,Shape__Length"
    ATTR_ACCUM_MODE = Only Use Result
    COMBINE_GEOM = Use Result
    FORMAT = ARCGISONLINEFEATURES
    INTERACT = NONE
    ORDER_RESULTS = No
    OUTPUT_FEATURES_DISPLAY = Schema and Data Features
    Scheme Boundaries -> Junction
Junction
    -> Junction_2

Bookmark: load: my content in agol (test)
Junction_2
    -> FeatureWriter [Scheme Boundaries]
Note: need to have publishing privilages in AGOL
FeatureWriter
    ARCGISONLINEFEATURES_ASYNC_WRITE = NO
    ARCGISONLINEFEATURES_DESTINATION_DATASETTYPE_VALIDATION = Yes
    ARCGISONLINEFEATURES_FEATURESERVICE = Scheme Boundaries
    ARCGISONLINEFEATURES_FEATURES_PER_REQUEST = 1000
    ARCGISONLINEFEATURES_FEATURE_SERVICE_HANDLING = CREATE_IF_MISSING
    ARCGISONLINEFEATURES_FEATURE_SERVICE_SELECTION_SOURCE = User
    ARCGISONLINEFEATURES_FOLDER_NAME = IAM
    ARCGISONLINEFEATURES_NC = hywell Esri ArcGIS Online
    ARCGISONLINEFEATURES_TARGET_WKID = 102100
    ARCGISONLINEFEATURES_USE_GLOBAL_ID = No
    DATASET_ATTR = _dataset
    FEATURE_TYPE_LIST_ATTR = _feature_types
    FORMAT = ARCGISONLINEFEATURES
    TOTAL_FEATURES_WRITTEN_ATTR = _total_features_written
