FME workspace buildings.fmw

Bookmark: datetime
Creator
    GEOMTYPE = Geometry Object
    NUM = 1
    CREATED -> DateTimeStamper
DateTimeStamper
    DATETIME_ATTR = origin_utc
    INCLUDE_FRAC_SECONDS = NO
    INCLUDE_OFFSET = NO
    STAMP_TYPE = datetime
    TIMEZONE = utc
    -> AttributeCreator
AttributeCreator
    ATTR_TABLE:
      SET_TO from (uint64) = 20240101000000
      SET_TO ta (buffer) = Queenstown-Lakes District
    -> DateTimeConverter
DateTimeConverter
    DATETIME_ATTR = origin_utc from
    OUT_FORMAT = %Y-%m-%dT%H:%M:%SZ
    PASSTHROUGH = NO
    REPAIR_INPUT = YES
    -> Junction
Junction
    -> Junction_2

Bookmark: exatract: building outlines from LINZ as CSV file
Junction_2
    -> _changeset [INITIATOR]
    -> _full [INITIATOR]
Note: _full [FeatureReader] / Reading: / Reader: / Dataset: https://data.linz.govt.nz/services;key=1cdb2df938344bc6aca0287bcbbc207e/wfs/layer-101290?SERVICE=WFS&VERSION=2.0.0&REQUEST=GetFeature&typeNames=layer-101290&cql_filter=territorial_auth ...
_full: FeatureReader
    ATTRIBUTES = CSV,"FID,__change__,building_id,name,use,suburb_locality,town_city,territorial_authority,capture_method,capture_source_group,capture_source_id,capture_source_name,capture_source_from,capture_source_to,last_modified,shape"
    ATTRS_TO_EXPOSE = building_id name use suburb_locality territorial_authority capture_method capture_source_group capture_source_id capture_source_name capture_source_from capture_source_to last_modified shape
    ATTR_ACCUM_MODE = Merge Initiator and Result
    ATTR_CONFLICT_RES = Use Result
    ATTR_IGNORE_NULLS = No
    COMBINE_GEOM = Use Result
    CSV2_CASE_SENSITIVE_FIELD_NAMES = Yes
    CSV2_CHUNK_SIZE = 100000
    CSV2_DATA_START_LINE = 2
    CSV2_DATE_INPUT_FORMAT = ISO
    CSV2_DELIMITER = auto
    CSV2_DELIMITER_DETECTION_ALGORITHM = EQUAL_FIELDS_PER_LINE
    CSV2_ENCODING = windows-1252
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = No
    CSV2_SCAN_ADDITIONAL_FIELDS = No
    CSV2_SCAN_MAX_ROWS = 250000
    CSV2_SCAN_TYPES = Yes
    CSV2_SKIP_DUPLICATE_DELIMITERS = No
    CSV2_STRING_TYPE_ATTRIBUTE_HANDLING = EXPLICIT_WIDTH
    CSV2_SUPPORTED_READER_ARCHIVE_EXTENSIONS = csv.gz,txt.gz
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_TYPE_ATTRIBUTE_HANDLING = STANDARD_TYPES
    CSV2_USE_CUSTOM_SCHEMA = NO
    DATASET = https://data.linz.govt.nz/services;key=1cdb2df938344bc6aca0287bcbbc207e/wfs/layer-101290?SERVICE=WFS&VERSION=2.0.0&REQUEST=GetFeature&typeNames=layer-101290&cql_filter=territorial_authority='@Value(ta)'&SRSNAME=EPSG:2193&outputFormat=csv
    FORMAT = CSV2
    INTERACT = NONE
    ORDER_RESULTS = No
    OUTPUT_FEATURES_DISPLAY = Schema and Data Features
    <OTHER> -> Junction_3
Junction_3
    -> Junction_4
_changeset: FeatureReader [off]
    ATTRIBUTES = CSV,"FID,__change__,building_id,name,use,suburb_locality,town_city,territorial_authority,capture_method,capture_source_group,capture_source_id,capture_source_name,capture_source_from,capture_source_to,last_modified,shape"
    ATTRS_TO_EXPOSE = __change building_id name use suburb_locality territorial_authority capture_method capture_source_group capture_source_id capture_source_name capture_source_from capture_source_to last_modified shape
    ATTR_ACCUM_MODE = Merge Initiator and Result
    ATTR_CONFLICT_RES = Use Result
    ATTR_IGNORE_NULLS = No
    COMBINE_GEOM = Use Result
    CSV2_CASE_SENSITIVE_FIELD_NAMES = Yes
    CSV2_CHUNK_SIZE = 100000
    CSV2_DATA_START_LINE = 2
    CSV2_DATE_INPUT_FORMAT = ISO
    CSV2_DELIMITER = auto
    CSV2_DELIMITER_DETECTION_ALGORITHM = EQUAL_FIELDS_PER_LINE
    CSV2_ENCODING = windows-1252
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = No
    CSV2_SCAN_ADDITIONAL_FIELDS = No
    CSV2_SCAN_MAX_ROWS = 250000
    CSV2_SCAN_TYPES = Yes
    CSV2_SKIP_DUPLICATE_DELIMITERS = No
    CSV2_STRING_TYPE_ATTRIBUTE_HANDLING = EXPLICIT_WIDTH
    CSV2_SUPPORTED_READER_ARCHIVE_EXTENSIONS = csv.gz,txt.gz
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_TYPE_ATTRIBUTE_HANDLING = STANDARD_TYPES
    CSV2_USE_CUSTOM_SCHEMA = NO
    DATASET = https://data.linz.govt.nz/services;key=1cdb2df938344bc6aca0287bcbbc207e/wfs/layer-101290-changeset?SERVICE=WFS&VERSION=2.0.0&REQUEST=GetFeature&typeNames=layer-101290-changeset&viewparams=from:@Value(from);to:@Value(origin_utc)&cql_filter=territorial_authority='@Value(ta)'&SRSNAME=EPSG:2193&outputFormat=csv
    FORMAT = CSV2
    INTERACT = NONE
    ORDER_RESULTS = No
    OUTPUT_FEATURES_DISPLAY = Schema and Data Features

Bookmark: transform: create geometry
Junction_4
    -> GeometryReplacer
GeometryReplacer
    KIND_LONG = OGC Well Known Text
    OGC_WKT_PRECISION_DISPLAY = 64-bit
    REMOVE_ATTRIBUTE = Yes
    SOURCE = @Value(shape)
    -> Deaggregator [off]
    -> GeometryCoercer [off]
    -> Junction_5
Deaggregator
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> AttributeCreator_2
AttributeCreator_2
    ATTR_TABLE = SET_TO id (varchar(200)) = FME_CONDITIONAL:DEFAULT_VALUE'@Value(building_id)'BOOL_OP;OR;COMPOSITE_TEST;1;TEST _part_number ATTRIBUTE_HAS_A_VALUE _FME_BLANK_STRING_'@Value(building_id)_@Value(_part_number)'FME_NUM_CONDITIONS2___
GeometryCoercer
    GQUERY:
      for $geom in //geometry
      where $geom/count(parent::geometry) = 0
      return number($geom/@fme_id)
    KIND = fme_polygon
    UNTOUCHED -> DonutHoleExtractor
DonutHoleExtractor
    DEAGGREGATE_INPUT = Yes
Junction_5
    -> Junction_6

Bookmark: load: 2shp
Junction_6
    -> AttributeRenamer
AttributeRenamer
    ATTR_TABLE:
      RENAME_SET_DEFAULT building_id > id
      RENAME_SET_DEFAULT suburb_locality > suburb
      RENAME_SET_DEFAULT territorial_authority > ta_area
    MISSING_INPUT_ATTRS = REMOVE
    -> DateTimeConverter_2
DateTimeConverter_2
    DATETIME_ATTR = origin_utc last_modified capture_source_from capture_source_to
    OUT_FORMAT = %Y%m%d%H%M%S
    PASSTHROUGH = NO
    REPAIR_INPUT = YES
    -> FeatureWriter_2 [Output]
    <REJECTED> -> FeatureWriter_2 [Output]
FeatureWriter_2
    COORDSYS = "ESRIWKT|NZGD_2000_New_Zealand_Transverse_Mercator|PROJCS["NZGD_2000_New_Zealand_Transverse_Mercator",GEOGCS["GCS_NZGD_2000",DATUM["D_NZGD_2000",SPHEROID["GRS_1980",6378137.0,298.257222101]],PRIMEM["Greenwich",0.0],UNIT["Degree",0.0174532925199433]],PROJECTION["Transverse_Mercator"],PARAMETER["False_Easting",1600000.0],PARAMETER["False_Northing",10000000.0],PARAMETER["Central_Meridian",173.0],PARAMETER["Scale_Factor",0.9996],PARAMETER["Latitude_Of_Origin",0.0],UNIT["Meter",1.0]]"
    DATASET = $(FME_MF_DIR_ENCODED)exports
    DATASET_ATTR = _dataset
    FEATURE_TYPE_LIST_ATTR = _feature_types
    FORMAT = SHAPEFILE
    SHAPEFILE_COMPRESSED_FILE = No
    SHAPEFILE_DATASET_SPLITTING = Yes
    SHAPEFILE_DATETIME_STORAGE = TIMESTAMP_STRING
    SHAPEFILE_DESTINATION_DATASETTYPE_VALIDATION = Yes
    SHAPEFILE_DIMENSION = AUTO
    SHAPEFILE_ENCODING = utf-8
    SHAPEFILE_ENFORCE_ATTRIBUTE_LIMIT = No
    SHAPEFILE_MEASURES_AS_Z = No
    SHAPEFILE_PERMIT_NONASCII_FIRST_ATTRNAME = Yes
    SHAPEFILE_REQUIRE_FIRST_ATTRNAME_ALPHA = Yes
    SHAPEFILE_SPATIAL_INDEXES = NONE
    SHAPEFILE_SURFACE_SOLID_STORAGE = PATCH
    TOTAL_FEATURES_WRITTEN_ATTR = _total_features_written
